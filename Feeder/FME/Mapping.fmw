FME workspace Mapping.fmw

Parameters:
- SourceDataset_SDE30 = @databasename@   # Source Esri ArcSDE Dataset
- DestDataset_MDB_ADO = @path@\GISPGDB\Input_Data.mdb   # Database Path
- SourceDataset_MSSQL_ADO = @sqldatabase@   # Database
- Password = @password@
- SourceDataset_SDE30_3 = @databasename@   # Source Esri ArcSDE Dataset
- Password_2 = @sqlpassword@

Readers:
- SDE30_1: SDE30 from $(SourceDataset_SDE30)
- MSSQL_ADO_1: MSSQL_ADO from $(SourceDataset_MSSQL_ADO)
- SDE30_2: SDE30 from $(SourceDataset_SDE30_3)

Writers:
- MDB_ADO_1: MDB_ADO to $(DestDataset_MDB_ADO)

HTCABLE (reader SDE30_2)
    attributes: OBJECTID integer, GISID char(50), NIN char(50), SubType smallint, ToGISID char(50), FromGISID char(50), FeederID char(12), FeederID2 char(12), FeederName char(50), Phasedesignation smallint, Voltage smallint, NumberofCore smallint, InsulationType char(5), ConnectionStatus char(12), ConductorMaterial char(9), NumberofCircuits char(14), CableSize char(20), Armoured char(3), RatedCurrent char(3), Cost char(10), CableType smallint, FeederCode char(3), Section char(22), Subdivision char(14), Division char(6), Circle char(6), Zone char(6), EAEquipment char(50), SAPID char(50), WorkOrderID char(50),
      SurveyorRemark char(250), MMELECTRICTRACEWEIGHT integer, FEEDERINFO integer, EquipmentID integer, SAPFunctionalLocation char(50), SSFacilityIDFK char(50), RMUFacilityIDFK char(50), created_user char(255), created_date date, last_edited_user char(255), last_edited_date date, TracingStatus integer, Enabled smallint, ShapeLength char(50), CYMESubstationCode char(5), Town char(30)
    -> AttributeFilter
AttributeFilter
    ATTR_VALUES = <Empty>,<Missing>,<Null>,<Unfiltered>
    ATTR_NAME = GISID
    <UNFILTERED> -> AttributeRemover
    <UNFILTERED> -> CYMESECTION
AVM_FEEDERLIST_PRIV_2: AttributeValueMapper
    VAL_ATTR = Town
    LUT = 01,ANGUL,02,BHUBANESWAR,03,CUTTACK,04,DHENKANAL,05,JAGATSINGHAPUR,06,JATNI,07,KENDRAPARA,08,KHORDHA,09,PARADEEP,10,PATTAMUNDAI,11,PURI,12,TALCHER
    SRC = Town
    DIRECTION = Forward (Source To Destination)
    -> AVM_HTCABLE_P
LTCABLE (reader SDE30_2)
    attributes: OBJECTID integer, GISID char(50), NIN char(50), SubType smallint, ToGISID char(50), FromGISID char(50), FeederID char(12), FeederID2 char(12), Phasedesignation smallint, Voltage smallint, NumberofCore smallint, InsulationType char(5), ConnectionStatus char(12), ConductorMaterial char(9), NumberofCircuits char(14), CableSize char(20), Armoured char(3), RatedCurrent char(4), Cost char(10), TracingStatus integer, CableType smallint, FeederCode char(3), Section char(22), Subdivision char(14), Division char(6), Circle char(6), Zone char(6), EAEquipment char(50), SAPID char(50), WorkOrderID char(50),
      SurveyorRemark char(250), MMELECTRICTRACEWEIGHT integer, FEEDERINFO integer, SAPFunctionalLocation char(50), DTCCode char(8), SSFacilityIDFK char(50), created_user char(255), created_date date, last_edited_user char(255), last_edited_date date, Enabled smallint, ShapeLength char(50), FeederName char(50), CYMESubstationCode char(5), Town char(30)
    -> AttributeFilter_2
AttributeFilter_2
    ATTR_VALUES = <Empty>,<Missing>,<Null>,<Unfiltered>
    ATTR_NAME = GISID
    <UNFILTERED> -> AttributeRemover_2
    <UNFILTERED> -> CYMESECTION
AttributeRemover_2
    REMOVE_ATTRS = last_edited_date,Zone,MMELECTRICTRACEWEIGHT,TracingStatus,OBJECTID,FEEDERINFO,SurveyorRemark,WorkOrderID,SAPID,Enabled,FeederID2,created_user,last_edited_user,Division,Cost,Armoured,EAEquipment,created_date,RatedCurrent
    -> Junction
    -> AVM_FEEDERLIST_PRIV_3
TGLINE_UNDERGROUNDLINE (writer MDB_ADO_1)
    attributes: SectionID text(64), DeviceNumber text(64), DeviceStage text(64), Flags long, InitFromEquipFlags text(64), LineCableID text(225), Length single, NumberOfCableInParallel text(20), Amps long, Amps_1 long, Amps_2 long, Amps_3 long, Amps_4 long, ConnectionStatus long, CoordX long, CoordY long, HarmonicModel long, EarthResistivity long, OperatingTemperature long, Height long, DistanceBetweenConductors long, BondingType long, CableConfiguration long, DuctMaterial long, Bundled long, Neutral1Type long, Neutral2Type long, Neutral3Type long, Neutral1ID text(64), Neutral2ID text(64),
      Neutral3ID text(64), AmpacityDeratingFactor long, FlowConstraintActive long, FlowConstraintUnit long, MaximumFlow long
HTCONDUCTOR (reader SDE30_2)
    attributes: OBJECTID integer, GISID char(50), NIN char(50), ToGISID char(50), FromGISID char(50), FeederID char(12), FeederID2 char(12), FeederName char(50), Phasedesignation smallint, Voltage smallint, NumberofWires smallint, ConnectionStatus char(12), TypeofSupport char(13), Configuration char(10), ConductorMaterial char(9), ConductorType char(11), ConductorSize char(9), NeutralConductor char(3), MatofNeutralConductor char(9), SizeofNeutralConductor char(9), AdditionalConductor char(3), SizeofAddConductor char(9), MatofAddConductor char(9), RatedCurrent char(3), OverheadHeight char(50), Cost char(10), SAPID char(50), FeederCode char(3), Section char(22), Subdivision char(14),
      Division char(6), Circle char(6), Zone char(6), EAEquipment char(50), WorkOrderID char(50), SurveyorRemark char(250), MMELECTRICTRACEWEIGHT integer, FEEDERINFO integer, EquipmentID integer, SAPFunctionalLocation char(50), Impedance char(50), Resistance char(50), SSFacilityIDFK char(50), RMUFacilityIDFK char(50), created_user char(255), created_date date, last_edited_user char(255), last_edited_date date, TracingStatus integer, Enabled smallint, ShapeLength char(50), CYMESubstationCode char(50), Town char(30)
    -> AttributeFilter_3
AttributeFilter_3
    ATTR_VALUES = <Empty>,<Missing>,<Null>,<Unfiltered>
    ATTR_NAME = GISID
    <UNFILTERED> -> AttributeRemover_3
    <UNFILTERED> -> CYMESECTION
LTCONDUCTOR (reader SDE30_2)
    attributes: OBJECTID integer, GISID char(50), NIN char(50), ToGISID char(50), FromGISID char(50), FeederID char(12), FeederID2 char(12), FeederName char(50), Phasedesignation smallint, Voltage smallint, NumberofWires smallint, ConnectionStatus char(12), TracingStatus integer, TypeofSupport char(13), Configuration char(12), ConductorMaterial char(9), ConductorType char(11), ConductorSize char(9), NeutralConductor char(3), MatofNeutralConductor char(9), SizeofNeutralConductor char(9), AdditionalConductor char(3), SizeofAddConductor char(9), MatofAddConductor char(9), RatedCurrent char(3), OverheadHeight char(50), Cost char(10), FeederCode char(3), Impedance char(50), DTCCode char(6),
      Resistance char(50), Section char(22), Subdivision char(14), Division char(6), Circle char(6), Zone char(6), EAEquipment char(50), SAPID char(50), WorkOrderID char(50), SurveyorRemark char(250), MMELECTRICTRACEWEIGHT integer, FEEDERINFO integer, SAPFunctionalLocation char(50), SSFacilityIDFK char(50), created_user char(255), created_date date, last_edited_user char(255), last_edited_date date, Enabled smallint, ShapeLength char(50), CYMESubstationCode char(5), Town char(30)
    -> AttributeFilter_4
AttributeFilter_4
    ATTR_VALUES = <Empty>,<Missing>,<Null>,<Unfiltered>
    ATTR_NAME = GISID
    <UNFILTERED> -> AttributeRemover_4
    <UNFILTERED> -> CYMESECTION
DISTRIBUTIONTRANSFORMER (reader SDE30_2)
    attributes: OBJECTID integer, Name char(250), DTCCode char(6), ExstingCESUDTCCode char(10), GISID char(50), NIN char(50), ToGISID char(50), FromGISID char(50), FeederID char(12), FeederID2 char(12), FeederName char(50), Phasedesignation smallint, CapacityInKVA smallint, PercentageImpedance char(10), HighSideVoltage smallint, HTProtection char(13), LTProtection char(4), LowSideVoltage smallint, TransformerMounting char(16), DTCondition char(6), TypeofCore char(9), VectorGroup char(24), TotalLoss char(50), CustomerClassCode char(12), MaximumTap char(20), MinimumTap char(20), NumberofSteps smallint, AdoptedTap char(20), StarRating char(6), CSPType char(17),
      MaximumDemand char(10), JobNumber char(50), DateofManufacturing date, ConsumptionType char(50), ConsumerCount char(5), HighSideCurrentRating char(20), LowSideCurrentRating char(20), CoolingType char(5), Earthing char(20), DateofCommissioning date, CompactType char(3), TertiaryVoltage smallint, DTCType char(19), WeightofOil char(8), OilQuantity char(6), TransformerWeight char(50), PercentageLoading char(50), NeutralEarthing char(3), TemperatureRisingWDG char(20), TemperatureRisingOil char(20), Ownership char(7), LifeSpan char(50), SwitchID char(10), TapLocation char(9), Configuration char(23), ConnectionStatus char(12), Make char(50), SerialNumber char(50), ManufacturingYear char(4), LastMaintenanceDate date,
      Warranty char(50), Cost char(10), FeederCode char(3), EquipmentID smallint, DTUtilization char(9), HTConsumerNumber char(12), SAPFunctionalLocation char(50), LoadTapChangerIndicator char(3), MagnetizingCurrent char(20), NumberofWays char(5), Section char(22), Subdivision char(14), Division char(6), Circle char(6), Zone char(6), EAEquipment char(50), SAPID char(50), WorkOrderID char(50), SurveyorRemark char(250), LocationCodeX double, LocationCodeY double, MMELECTRICTRACEWEIGHT integer, FEEDERINFO integer, FacilityID char(20), StationFacilityIDFK char(50), Metering char(8), created_user char(255), created_date date, last_edited_user char(255), last_edited_date date,
      Enabled smallint, NoLoadLoss char(10), CopperLoss char(10), TotalLoad float, CYMESubstationCode char(50), Town char(30)
    -> CYMESECTION
    -> AttributeRemover_6
    -> PointOnLineOverlayer [POINT]
GIS_DT (writer MDB_ADO_1)
    attributes: DEVICETYPE text(200), OBJECTID long, Name text(250), DTCCode text(50), ExstingCESUDTCCode text(10), GISID text(50), NIN text(50), ToGISID text(50), FromGISID text(50), FeederID text(50), FeederName text(50), Phasedesignation integer, CapacityInKVA integer, PercentageImpedance text(10), HighSideVoltage integer, LowSideVoltage integer, TransformerMounting text(30), DTCondition text(6), TypeofCore text(9), VectorGroup text(50), NumberofSteps integer, DateofManufacturing datetime, CoolingType text(20), DateofCommissioning datetime, WeightofOil text(8), SwitchID text(20), Configuration text(50), ConnectionStatus text(12), FeederCode text(50), EquipmentID integer,
      DTUtilization text(9), HTConsumerNumber text(12), SAPFunctionalLocation text(50), NumberofWays text(5), Section text(22), Subdivision text(50), Division text(50), Circle text(50), Zone text(50), LocationCodeX double, LocationCodeY double, StationFacilityIDFK text(50), Metering text(8), Enabled integer, CYMESubstationCode text(50), Town text(30), TG_PHASE text(200), TG_HighSideVoltage text(200), TG_LowSideVoltage text(200), TG_COOLINGTYPE text(200), TG_CONNECTIONSTATE text(200), TG_TransformerMounting text(200), TG_EQUIPMENTID text(200)
TGDEVICE_DISTRIBUTIONTRANSFORMER (writer MDB_ADO_1)
    attributes: SectionID text(200), Location text(200), EqID text(200), DeviceNumber text(200), DeviceStage text(200), Flags text(200), CoordX text(200), CoordY text(200), Conn text(200), PrimTap text(200), SecondaryTap text(200), RgPrim text(200), XgPrim text(200), RgSec text(200), XgSec text(200), ODPrimPh text(200), PrimaryBaseVoltage text(200), SecondaryBaseVoltage text(200), FromNodeID text(200), SettingOption text(200), SetPoint text(200), ControlType text(200), LowerBandWidth text(200), UpperBandWidth text(200), TapLocation text(200), InitialTapPosition text(200), InitialTapPositionMode text(200), Tap text(200), MaxBuck text(200), MaxBoost text(200),
      CT text(200), PT text(200), Rset text(200), Xset text(200), FirstHouseHigh text(200), FirstHouseLow text(200), PhaseON text(200), AtSectionID text(200), MasterID text(200), FaultIndicator text(200), PhaseShiftType text(200), GammaPhaseShift text(200), CTPhase text(200), PrimaryCornerGroundedPhase text(200), SecondaryCornerGroundedPhase text(200), ConnectionStatus text(200), Reversible text(200)
SWITCHGEAR (reader SDE30_2)
    attributes: OBJECTID integer, InstalledLocation smallint, LocationID char(50), GISID char(50), NIN char(50), SubType smallint, FeederID char(12), FeederID2 char(12), FeederName char(50), Phasedesignation smallint, Voltage smallint, InsulationType char(7), Mechanism smallint, AuxiliarySupply char(2), SymmetricalBreakingCurrent char(10), RatedPower char(50), CTPTCombined char(3), DTCCode char(6), MakingCapacity char(50), OperatingSequence char(50), Make char(50), SerialNumber char(50), ManufacturingYear char(4), DateofCommissioning date, LastMaintenanceDate date, Warranty char(50), Cost char(10), AncillaryRole smallint, NormalStatus integer, NormalPositionR integer,
      NormalPositionY integer, NormalPositionB integer, PresentPositionR integer, PresentPositionY integer, PresentPositionB integer, RatedCurrent char(4), FeederCode char(3), EquipmentID integer, SAPFunctionalLocation char(50), ConnectionStatus char(50), Section char(22), Subdivision char(14), Division char(6), Circle char(6), Zone char(6), EAEquipment char(50), SAPID char(50), WorkOrderID char(50), SurveyorRemark char(250), LocationCodeX double, LocationCodeY double, MMELECTRICTRACEWEIGHT integer, FEEDERINFO integer, RMUFacilityIDFK char(50), PillarFacilityIDFK char(50), StationFacilityIDFK char(50), created_user char(255), created_date date, last_edited_user char(255), last_edited_date date,
      Enabled smallint, CYMESubstationCode char(5), Town char(30)
    -> Junction_8
    -> AttributeRemover_5
    -> CYMESECTION
Note: AttributeCreator : Input
Junction_8
    -> Junction_9
TGDEVICE_CIRCUITBREAKER (writer MDB_ADO_1)
    attributes: SectionID text(200), Location text(200), EqID text(200), DeviceNumber text(200), DeviceStage text(200), Flags text(200), InitFromEquipFlags text(200), CoordX text(200), CoordY text(200), ClosedPhase text(200), Locked text(200), RC text(200), NStatus text(200), TCCID text(200), PhPickup text(200), GrdPickup text(200), Alternate text(200), PhAltPickup text(200), GrdAltPickup text(200), FromNodeID text(200), EnableReclosing text(200), FaultIndicator text(200), EnableFuseSaving text(200), MinRatedCurrentForFuseSaving text(200), Automated text(200), SensorMode text(200), Strategic text(200), RestorationMode text(200), ConnectionStatus text(200), ByPassOnRestoration text(200),
      Speed text(200), SeqOpFirstPhase text(200), SeqOpFirstGround text(200), SeqOpLockoutPhase text(200), SeqOpLockoutGround text(200), SeqResetTime text(200), SeqReclosingTime1 text(200), SeqReclosingTime2 text(200), SeqReclosingTime3 text(200), Reversible text(200)
SWITCH (reader SDE30_2)
    attributes: OBJECTID integer, GISID char(50), NIN char(50), SubType smallint, InstalledLocation smallint, LocationID char(50), FeederID char(12), FeederID2 char(12), FeederName char(50), Phasedesignation smallint, Voltage smallint, Mechanism smallint, NormalStatus integer, NormalPositionR integer, NormalPositionY integer, NormalPositionB integer, PresentPositionR integer, PresentPositionY integer, PresentPositionB integer, NormalRatedCurrent smallint, ReactiveBreakingCurrent char(50), BreakingCurrent char(10), DTCCode char(6), Make char(50), SerialNumber char(50), ManufacturingYear char(4), DateofCommissioning date, LastMaintenanceDate date, Warranty char(50), Cost char(10),
      FeederCode char(3), SAPFunctionalLocation char(50), ConnectionStatus char(12), Section char(22), Subdivision char(14), Division char(6), Circle char(6), Zone char(6), EAEquipment char(50), SAPID char(50), WorkOrderID char(50), SurveyorRemark char(250), LocationCodeX double, LocationCodeY double, MMELECTRICTRACEWEIGHT integer, FEEDERINFO integer, SSFacilityIDFK char(50), RMUFacilityIDFK char(50), PillarFacilityIDFK char(50), StationFacilityIDFK char(50), created_user char(255), created_date date, last_edited_user char(255), last_edited_date date, Enabled smallint, CYME char(11), CYMESubstationCode char(5), Town char(30)
    -> PointOnLineOverlayer [POINT]
    -> CYMESECTION
    -> AttributeRemover_7
TGDEVICE_SWITCH (writer MDB_ADO_1)
    attributes: SectionID text(200), Location text(200), EqID text(200), DeviceNumber text(200), DeviceStage text(200), Flags text(200), InitFromEquipFlags text(200), CoordX text(200), CoordY text(200), ClosedPhase text(200), Locked text(200), RC text(200), NStatus text(200), PhPickup text(200), GrdPickup text(200), Alternate text(200), PhAltPickup text(200), GrdAltPickup text(200), FromNodeID text(200), FaultIndicator text(200), Automated text(200), SensorMode text(200), Strategic text(200), RestorationMode text(200), ConnectionStatus text(200), ByPassOnRestoration text(200), Reversible text(200)
FUSE (reader SDE30_2)
    attributes: OBJECTID integer, InstalledLocation smallint, LocationID char(50), Name char(250), GISID char(50), NIN char(50), FeederID char(12), FeederID2 char(12), FeederName char(50), Voltage smallint, Type smallint, Phasedesignation smallint, NormalStatus integer, NormalPositionR integer, NormalPositionY integer, NormalPositionB integer, PresentPositionR integer, PresentPositionY integer, PresentPositionB integer, FaultCurrent smallint, DTCCode char(6), ConnectionStatus char(12), Cost char(10), FeederCode char(3), Class smallint, Section char(22), Subdivision char(14), Division char(5), Circle char(6), Zone char(6),
      EAEquipment char(50), SAPID char(50), WorkOrderID char(50), SurveyorRemark char(250), LocationCodeX double, LocationCodeY double, MMELECTRICTRACEWEIGHT integer, FEEDERINFO integer, SAPFunctionalLocation char(50), StationFacilityIDFK char(50), RMUFacilityIDFK char(50), SSFacilityIDFK char(50), PillarFacilityIDFK char(50), created_user char(255), created_date date, last_edited_user char(255), last_edited_date date, Enabled smallint, Rating float, CYMESubstationCode char(5), LTCircuitCode char(1), Town char(30)
    -> CYMESECTION
    -> AttributeRemover_8
TGDEVICE_FUSE (writer MDB_ADO_1)
    attributes: SectionID text(200), Location text(200), EqID text(200), DeviceNumber text(200), DeviceStage text(200), Flags text(200), InitFromEquipFlags text(200), CoordX text(200), CoordY text(200), ClosedPhase text(200), Locked text(200), RC text(200), NStatus text(200), TCCID text(200), PhPickup text(200), GrdPickup text(200), Alternate text(200), PhAltPickup text(200), GrdAltPickup text(200), FromNodeID text(200), FaultIndicator text(200), Strategic text(200), RestorationMode text(200), ConnectionStatus text(200), ByPassOnRestoration text(200), Reversible text(200)
SHUNTCAPACITOR (reader SDE30_2)
    attributes: OBJECTID integer, Name char(250), GISID char(50), NIN char(50), FeederID char(12), FeederID2 char(50), FeederName char(50), InstalledLocation smallint, Voltage smallint, Phasedesignation smallint, CapacityInKVAR float, VectorGroup char(24), DTCCode char(6), Make char(50), SerialNumber char(50), Cost char(50), Setting char(21), FeederCode char(3), ConnectionStatus char(12), MultiplyingFactor char(10), Section char(22), Subdivision char(14), Division char(6), Circle char(6), Zone char(6), EAEquipment char(50), SAPID char(50), WorkOrderID char(50), SurveyorRemark char(250), LocationCodeX double,
      LocationCodeY double, MMELECTRICTRACEWEIGHT integer, FEEDERINFO integer, EquipmentIDFK integer, SAPFunctionalLocation char(50), StationFacilityIDFK char(50), created_user char(255), created_date date, last_edited_user char(255), last_edited_date date, Enabled smallint, ShuntReactance char(10), CYMESubstationCode char(50), Town char(30)
    -> CYMESECTION
    -> AttributeRemover_9
TGDEVICE_SHUNTCAPACITOR (writer MDB_ADO_1)
    attributes: SectionID text(200), DeviceNumber text(200), DeviceStage text(200), Flags text(200), InitFromEquipFlags text(200), Location text(200), Connection text(200), FixedKVARA text(200), FixedKVARB text(200), FixedKVARC text(200), FixedLossesA text(200), FixedLossesB text(200), FixedLossesC text(200), SwitchedKVARA text(200), SwitchedKVARB text(200), SwitchedKVARC text(200), SwitchedLossesA text(200), SwitchedLossesB text(200), SwitchedLossesC text(200), ByPhase text(200), VoltageOverride text(200), VoltageOverrideOn text(200), VoltageOverrideOff text(200), VoltageOverrideDeadband text(200), KV text(200), Control text(200), OnValueA text(200), OnValueB text(200), OnValueC text(200), OffValueA text(200),
      OffValueB text(200), OffValueC text(200), SwitchingMode text(200), InitiallyClosedPhase text(200), CurrentClosedPhase text(200), ControllingPhase text(200), SensorLocation text(200), ControlledNodeId text(200), PythonDeviceScriptID text(200), ShuntCapacitorID text(200), ConnectionStatus text(200), CTConnection text(200), InterruptingRating text(200)
Note: ArcGIS CYME FME Workbench file / Tech-Gration for ADCC@CESU / Version 1.0 / MSSQL ArcSDE / Author: Rajib Kumar / Created: Augest 01th, 2017 / Last Modified: August 05, 2017 / Trident Techlabs Pvt Ltd
PointOnLineOverlayer
    OV_ATTR = _OBJECTID
    TOLERANCE = 0.02
    LINE -> CYMESECTION
CYMESECTION
    SHAPE_STLENGTH__ = @Value(SHAPE_STLength__)
    DIVISION = @Value(Division)
    FEEDERID = @Value(FeederID)
    PHASEDESIGNATION = @Value(Phasedesignation)
    CIRCLE = @Value(Circle)
    OBJECTID = @Value(OBJECTID)
    GISID = @Value(GISID)
    Output_BREAKERSECTION -> DEVICESECTION [BREAKER]
    Output_FUSESECTION -> DEVICESECTION [FUSE]
    Output_SWITCHSECTION -> DEVICESECTION [SWITCH]
    Output_node -> NODES (writer MDB_ADO_1)
    Output_node -> TempNode (writer MDB_ADO_1)
    Output_node -> Junction_2
    Output_node -> Junction_10
    Output_DTSECTION -> DEVICESECTION [DT]
    Output_Section -> FeatureMerger_3 [SUPPLIER]
    Output_TempNode -> FeatureMerger_3 [REQUESTOR]
    Output_TGLINE -> TG_LINE (writer MDB_ADO_1)
    Output_Prisec -> PRISEC (writer MDB_ADO_1)
    Output_Prisec -> CYMEBREAKINGSECTION
    Output_Prisec -> Junction_3
    Output_TempIntermediate_Node -> TGNODE_INTERMEDIATENODES (writer MDB_ADO_1)
NODES (writer MDB_ADO_1)
    attributes: GISID text(30), X text(30), Y text(30)
TG_LINE (writer MDB_ADO_1)
    attributes: GISID text(255), FeederID text(50), TG_PHASE text(20), Length double
PRISEC (writer MDB_ADO_1)
    attributes: Index text(30), GISID text(255), Coordinates text(255), X text(255), Y text(255), FeederId text(255)
Note: CYMELOAD : PRISEC
Junction_2
    -> Junction_5
FinalSection (writer MDB_ADO_1)
    attributes: SectionId text(200), FromNodeId text(200), FromNodeIndex text(200), ToNodeId text(200), ToNodeIndex text(200), Phase text(200), ZoneID text(200), SubNetworkId text(200), EnvironmentID text(200)
Note: CYMEBREAKINGSECTION : Output_Overhead_TempSection_Breaked
Junction_13
    -> TGLINE_OVERHEADLINE (writer MDB_ADO_1)
TGLINE_OVERHEADLINE (writer MDB_ADO_1)
    attributes: SectionID text(64), DeviceNumber text(64), DeviceStage text(64), Flags long, InitFromEquipFlags text(64), LineCableID text(225), Length single, ConnectionStatus long, CoordX long, CoordY text(20), HarmonicModel integer, FlowConstraintActive integer, FlowConstraintUnit integer, MaximumFlow integer, SeriesCompensationActive integer, MaxReactanceMultiplier integer, SeriesCompensationCost integer
Note: CYMEBREAKINGSECTION : Output_BreakedTempNode
Junction_7
    -> TempNode (writer MDB_ADO_1)
DEVICESECTION
    TG_DTGISID = @Value(TG_DTGISID)
    SECTIONID = @Value(SectionId)
    TG_SWITCHGISID = @Value(TG_SWITCHGISID)
    TONODEID = @Value(ToNodeId)
    TG_FUSEGISID = @Value(TG_FUSEGISID)
    FROMNODEID = @Value(FromNodeId)
    NODEID = @Value(NodeId)
    SWITCHID = @Value(SwitchID)
    BREAKER -> TGSECTION_BREAKER (writer MDB_ADO_1)
    DT -> TGSECTION_DT (writer MDB_ADO_1)
    SWITCH -> TGSECTION_SWITCH (writer MDB_ADO_1)
    FUSE -> TGSECTION_FUSE (writer MDB_ADO_1)
TGSECTION_BREAKER (writer MDB_ADO_1)
    attributes: GISID text(50), NodeId text(200), TG_BREAKERGISID text(200), SectionId text(200)
TGSECTION_DT (writer MDB_ADO_1)
    attributes: GISID text(50), NodeId text(200), TG_DTGISID text(200), SectionId text(200)
TGSECTION_SWITCH (writer MDB_ADO_1)
    attributes: GISID text(50), NodeId text(200), TG_SWITCHGISID text(200), SectionId text(200)
TGSECTION_FUSE (writer MDB_ADO_1)
    attributes: GISID text(50), NodeId text(200), TG_FUSEGISID text(200), SectionId text(200)
Note: FeatureMerger_5 : Requestor
Junction_10
    -> Junction_11
Note: CYMELOAD : LTCABLE
Junction_3
    -> Junction_4
TGSECTION_DT2 (writer MDB_ADO_1)
    attributes: GISID text(50), NodeId text(200), TG_DTGISID text(200), SectionId text(200)
TGSECTION_SWITCH2 (writer MDB_ADO_1)
    attributes: GISID text(50), NodeId text(200), TG_SWITCHGISID text(200), SectionId text(200)
TGSECTION_FUSE2 (writer MDB_ADO_1)
    attributes: GISID text(50), NodeId text(200), TG_FUSEGISID text(200), SectionId text(200)
SPOTLOADUDD: AttributeCreator
    ATTR_TABLE:
      SET_TO DeviceNumber = @Value(GISID)
      SET_TO DeviceType = 20
      SET_TO DataId = FEEDERNAME
      SET_TO DataType = 8
      SET_TO DataValue = @Value(FeederName)

Bookmark: LINECONFIG UNDERGROUNDLINE and OVERHEADLINE
AttributeRemover
    REMOVE_ATTRS = created_date,last_edited_user,Enabled,TracingStatus,FEEDERINFO,Armoured,OBJECTID,FeederID2,Division,MMELECTRICTRACEWEIGHT,SAPID,SurveyorRemark,Cost,EAEquipment,WorkOrderID,created_user,RatedCurrent,Zone,last_edited_date
    -> AVM_FEEDERLIST_PRIV_2
AVM_HTCABLE_P: AttributeValueMapper
    DEFAULT_VALUE = 0
    VAL_ATTR = TG_PHASE
    LUT = 1,1,2,1,3,2,4,1,5,2,6,2,7,3
    SRC = Phasedesignation
    DIRECTION = Forward (Source To Destination)
    -> AVM_HTCABLE_V
AVM_HTCABLE_V: AttributeValueMapper
    DEFAULT_VALUE = KV
    VAL_ATTR = TG_VOLTAGE
    LUT = 340,11KV,360,22KV,380,33KV,80,66KV,90,100KV,110,132KV,150,220KV,260,400KV,120,0.11KV,160,0.24KV,210,0.43KV
    SRC = Voltage
    DIRECTION = Forward (Source To Destination)
    -> AVM_HTCABLE_SUBTYPE
AVM_HTCABLE_SUBTYPE: AttributeValueMapper
    DEFAULT_VALUE = 0
    VAL_ATTR = TG_SUBTYPE
    LUT = 0,0,1,0,2,0,3,0
    SRC = SubType
    DIRECTION = Forward (Source To Destination)
    -> AVM_HTCABLE_CONNECTIONSTATE
AVM_HTCABLE_CONNECTIONSTATE: AttributeValueMapper
    VAL_ATTR = TG_CONNECTIONSTATE
    LUT = 1,0,2,1,3,0,4,1
    SRC = ConnectionStatus
    DIRECTION = Forward (Source To Destination)
    -> AVM_HTCABLE_CABLETYPE
AVM_HTCABLE_CABLETYPE: AttributeValueMapper
    VAL_ATTR = TG_CABLETYPE
    LUT = 1,HT CABLE,2,SERVICE CABLE
    SRC = CableType
    DIRECTION = Forward (Source To Destination)
    -> LengthCalculator_2
LengthCalculator_2
    MULT = 1
    LEN_ATTR = Length
    DIM = 2
    -> StringConcatenator
StringConcatenator
    PARM_LINE = @Value(TG_PHASE)P_@Value(TG_VOLTAGE)_@Value(NumberofCore)C_@Value(CableSize)SQMM_@Value(InsulationType)_@Value(ConductorMaterial)
    VAL_ATTR = TG_EQUIPMENTID
    ACTION = Create New Attribute
    -> AttributeCreator_11
    -> GIS_HTCABLE (writer MDB_ADO_1)
    -> Junction_14
GIS_HTCABLE (writer MDB_ADO_1)
    attributes: GISID text(50), NIN text(50), SubType integer, ToGISID text(50), FromGISID text(50), FeederID text(12), FeederName text(50), Phasedesignation integer, Voltage integer, NumberofCore integer, InsulationType text(5), ConnectionStatus text(12), ConductorMaterial text(9), NumberofCircuits text(14), CableSize text(20), CableType integer, FeederCode text(3), Section text(22), Subdivision text(14), Circle text(6), EquipmentID long, SAPFunctionalLocation text(50), SSFacilityIDFK text(50), RMUFacilityIDFK text(50), ShapeLength text(50), CYMESubstationCode text(5), Town text(30), TG_PHASE text(200), TG_VOLTAGE text(200), TG_SUBTYPE text(200),
      TG_CONNECTIONSTATE text(200), TG_CABLETYPE text(200), Length text(200), TG_EQUIPMENTID text(200)
Note: AttributeCreator_3 : Input
Junction_14
    -> Junction_15
Note: CYMELOAD : LTCABLE
Junction
AVM_FEEDERLIST_PRIV_3: AttributeValueMapper
    VAL_ATTR = Town
    LUT = 01,ANGUL,02,BHUBANESWAR,03,CUTTACK,04,DHENKANAL,05,JAGATSINGHAPUR,06,JATNI,07,KENDRAPARA,08,KHORDHA,09,PARADEEP,10,PATTAMUNDAI,11,PURI,12,TALCHER
    SRC = Town
    DIRECTION = Forward (Source To Destination)
    -> AVM_LTCABLE_P
AVM_LTCABLE_P: AttributeValueMapper
    DEFAULT_VALUE = 0
    VAL_ATTR = TG_PHASE
    LUT = 1,1,2,1,3,2,4,1,5,2,6,2,7,3
    SRC = Phasedesignation
    DIRECTION = Forward (Source To Destination)
    -> AVM_LTCABLE_V
AVM_LTCABLE_V: AttributeValueMapper
    DEFAULT_VALUE = KV
    VAL_ATTR = TG_VOLTAGE
    LUT = 340,11KV,360,22KV,380,33KV,80,66KV,90,100KV,110,132KV,150,220KV,260,400KV,120,0.11KV,160,0.24KV,210,0.43KV
    SRC = Voltage
    DIRECTION = Forward (Source To Destination)
    -> AVM_LTCABLE_SUBTYPE
AVM_LTCABLE_SUBTYPE: AttributeValueMapper
    DEFAULT_VALUE = 0
    VAL_ATTR = TG_SUBTYPE
    LUT = 0,1,1,1,2,1,3,0
    SRC = SubType
    DIRECTION = Forward (Source To Destination)
    -> AVM_LTCABLE_CONNECTIONSTATE
AVM_LTCABLE_CONNECTIONSTATE: AttributeValueMapper
    VAL_ATTR = TG_CONNECTIONSTATE
    LUT = 1,0,2,1,3,0,4,1
    SRC = ConnectionStatus
    DIRECTION = Forward (Source To Destination)
    -> AVM_LTCABLE_CABLETYPE
AVM_LTCABLE_CABLETYPE: AttributeValueMapper
    VAL_ATTR = TG_CABLETYPE
    LUT = 1,HT CABLE,2,SERVICE CABLE
    SRC = CableType
    DIRECTION = Forward (Source To Destination)
    -> StringReplacer_2
StringReplacer_2
    FIND_TEXT = " "
    SRC_ATTRS = FeederID,GISID,CableSize,ConductorMaterial,CableType
    CASE = NO
    REGEXP = NO
    NO_MATCH = _FME_NO_OP_
    -> LengthCalculator
LengthCalculator
    MULT = 1
    LEN_ATTR = Length
    DIM = 2
    -> StringConcatenator_2
StringConcatenator_2
    PARM_LINE = @Value(TG_PHASE)P_@Value(TG_VOLTAGE)_@Value(NumberofCore)C_@Value(CableSize)SQMM_@Value(InsulationType)_@Value(ConductorMaterial)
    VAL_ATTR = TG_EQUIPMENTID
    ACTION = Create New Attribute
    -> AttributeCreator_11
    -> GIS_LTCABLE (writer MDB_ADO_1)
    -> Junction_16
AttributeCreator_11
    ATTR_TABLE:
      SET_TO SectionID = @Value(GISID)
      SET_TO DeviceNumber = @Value(GISID)
      SET_TO ConnectionStatus = @Value(TG_CONNECTIONSTATE)
      SET_TO LineCableID = @Value(TG_EQUIPMENTID)
    -> TGLINE_UNDERGROUNDLINE (writer MDB_ADO_1)
GIS_LTCABLE (writer MDB_ADO_1)
    attributes: GISID text(50), NIN text(50), SubType integer, ToGISID text(50), FromGISID text(50), FeederID text(12), Phasedesignation integer, Voltage integer, NumberofCore integer, InsulationType text(5), ConnectionStatus text(12), ConductorMaterial text(9), NumberofCircuits text(14), CableSize text(20), CableType integer, FeederCode text(3), Section text(22), Subdivision text(14), Circle text(6), SAPFunctionalLocation text(50), DTCCode text(8), SSFacilityIDFK text(50), ShapeLength text(50), FeederName text(50), CYMESubstationCode text(5), Town text(30), TG_PHASE text(200), TG_VOLTAGE text(200), TG_SUBTYPE text(200), TG_CONNECTIONSTATE text(200),
      TG_CABLETYPE text(200), Length text(200), TG_EQUIPMENTID text(200)
Junction_16
    -> Junction_17
AttributeRemover_3
    REMOVE_ATTRS = Cost,last_edited_date,FEEDERINFO,OverheadHeight,created_user,FeederID2,TracingStatus,WorkOrderID,created_date,EAEquipment,SurveyorRemark,last_edited_user,Resistance
    -> AVM_FEEDERLIST_PRIV_4
AVM_FEEDERLIST_PRIV_4: AttributeValueMapper
    VAL_ATTR = Town
    LUT = 01,ANGUL,02,BHUBANESWAR,03,CUTTACK,04,DHENKANAL,05,JAGATSINGHAPUR,06,JATNI,07,KENDRAPARA,08,KHORDHA,09,PARADEEP,10,PATTAMUNDAI,11,PURI,12,TALCHER
    SRC = Town
    DIRECTION = Forward (Source To Destination)
    -> AVM_HTCONDUCTOR_P
AVM_HTCONDUCTOR_P: AttributeValueMapper
    DEFAULT_VALUE = 0
    VAL_ATTR = TG_PHASE
    LUT = 1,1,2,1,3,2,4,1,5,2,6,2,7,3
    SRC = Phasedesignation
    DIRECTION = Forward (Source To Destination)
    -> AVM_HTCONDUCTOR_V
AVM_HTCONDUCTOR_V: AttributeValueMapper
    DEFAULT_VALUE = KV
    VAL_ATTR = TG_VOLTAGE
    LUT = 340,11KV,360,22KV,380,33KV,80,66KV,90,100KV,110,132KV,150,220KV,260,400KV,120,0.11KV,160,0.24KV,210,0.43KV
    SRC = Voltage
    DIRECTION = Forward (Source To Destination)
    -> StringReplacer
StringReplacer
    FIND_TEXT = " "
    SRC_ATTRS = ConductorSize,FeederID,ConductorType,ConductorMaterial
    CASE = NO
    REGEXP = NO
    NO_MATCH = _FME_NO_OP_
    -> AVM_HTCONDUCTOR_CONNECTIONSTATE
AVM_HTCONDUCTOR_CONNECTIONSTATE: AttributeValueMapper
    VAL_ATTR = TG_CONNECTIONSTATE
    LUT = 1,0,2,1
    SRC = ConnectionStatus
    DIRECTION = Forward (Source To Destination)
    -> LengthCalculator_3
LengthCalculator_3
    MULT = 1
    LEN_ATTR = Length
    DIM = 2
    -> StringConcatenator_3
StringConcatenator_3
    PARM_LINE = @Value(TG_PHASE)P_@Value(TG_VOLTAGE)_@Value(ConductorSize)_@Value(ConductorType)_@Value(ConductorMaterial)_@Value(Configuration)C
    VAL_ATTR = TG_EQUIPMENTID
    ACTION = Create New Attribute
    -> AttributeCreator_8
    -> GIS_HTCONDUCTOR (writer MDB_ADO_1)
    -> Junction_18
GIS_HTCONDUCTOR (writer MDB_ADO_1)
    attributes: OBJECTID long, GISID text(50), NIN text(50), ToGISID text(50), FromGISID text(50), FeederID text(12), FeederName text(50), Phasedesignation integer, Voltage integer, NumberofWires integer, ConnectionStatus text(12), TypeofSupport text(13), Configuration text(10), ConductorMaterial text(9), ConductorType text(11), ConductorSize text(9), NeutralConductor text(3), MatofNeutralConductor text(9), SizeofNeutralConductor text(9), AdditionalConductor text(3), SizeofAddConductor text(9), MatofAddConductor text(9), RatedCurrent text(3), SAPID text(50), FeederCode text(3), Section text(22), Subdivision text(14), Division text(6), Circle text(6), Zone text(6),
      MMELECTRICTRACEWEIGHT long, EquipmentID long, SAPFunctionalLocation text(50), Impedance text(50), SSFacilityIDFK text(50), RMUFacilityIDFK text(50), Enabled integer, ShapeLength text(50), CYMESubstationCode text(50), Town text(30), TG_PHASE text(200), TG_VOLTAGE text(200), TG_CONNECTIONSTATE text(200), Length text(200), TG_EQUIPMENTID text(200)
Junction_18
    -> Junction_19
AttributeRemover_4
    REMOVE_ATTRS = Cost,last_edited_date,FEEDERINFO,created_user,SAPID,FeederID2,TracingStatus,Impedance,WorkOrderID,created_date,EAEquipment,SurveyorRemark,MMELECTRICTRACEWEIGHT,last_edited_user,Resistance
    -> AVM_FEEDERLIST_PRIV_6
AVM_FEEDERLIST_PRIV_6: AttributeValueMapper
    VAL_ATTR = Town
    LUT = 01,ANGUL,02,BHUBANESWAR,03,CUTTACK,04,DHENKANAL,05,JAGATSINGHAPUR,06,JATNI,07,KENDRAPARA,08,KHORDHA,09,PARADEEP,10,PATTAMUNDAI,11,PURI,12,TALCHER
    SRC = Town
    DIRECTION = Forward (Source To Destination)
    -> AVM_LTCONDUCTOR_P
AVM_LTCONDUCTOR_P: AttributeValueMapper
    DEFAULT_VALUE = 0
    VAL_ATTR = TG_PHASE
    LUT = 1,1,2,1,3,2,4,1,5,2,6,2,7,3
    SRC = Phasedesignation
    DIRECTION = Forward (Source To Destination)
    -> AVM_LTCONDUCTOR_V
AVM_LTCONDUCTOR_V: AttributeValueMapper
    DEFAULT_VALUE = KV
    VAL_ATTR = TG_VOLTAGE
    LUT = 340,11KV,360,22KV,380,33KV,80,66KV,90,100KV,110,132KV,150,220KV,260,400KV,120,0.11KV,160,0.24KV,210,0.43KV
    SRC = Voltage
    DIRECTION = Forward (Source To Destination)
    -> StringReplacer_3
StringReplacer_3
    FIND_TEXT = " "
    SRC_ATTRS = ConductorSize,FeederID,ConductorType,ConductorMaterial
    CASE = NO
    REGEXP = NO
    NO_MATCH = _FME_NO_OP_
    -> AVM_LTCONDUCTOR_CONNECTIONSTATE
AVM_LTCONDUCTOR_CONNECTIONSTATE: AttributeValueMapper
    VAL_ATTR = TG_CONNECTIONSTATE
    LUT = 1,0,2,1
    SRC = ConnectionStatus
    DIRECTION = Forward (Source To Destination)
    -> LengthCalculator_4
LengthCalculator_4
    MULT = 1
    LEN_ATTR = Length
    DIM = 2
    -> StringConcatenator_4
StringConcatenator_4
    PARM_LINE = @Value(TG_PHASE)P_@Value(TG_VOLTAGE)_@Value(ConductorSize)_@Value(ConductorType)_@Value(ConductorMaterial)_@Value(Configuration)C
    VAL_ATTR = TG_EQUIPMENTID
    ACTION = Create New Attribute
    -> AttributeCreator_8
    -> GIS_LTCONDUCTOR (writer MDB_ADO_1)
    -> Junction_20
GIS_LTCONDUCTOR (writer MDB_ADO_1)
    attributes: OBJECTID long, GISID text(50), NIN text(50), ToGISID text(50), FromGISID text(50), FeederID text(12), FeederName text(50), Phasedesignation integer, Voltage integer, NumberofWires integer, ConnectionStatus text(12), TypeofSupport text(13), Configuration text(12), ConductorMaterial text(9), ConductorType text(11), ConductorSize text(9), NeutralConductor text(3), MatofNeutralConductor text(9), SizeofNeutralConductor text(9), AdditionalConductor text(3), SizeofAddConductor text(9), MatofAddConductor text(9), RatedCurrent text(3), OverheadHeight text(50), FeederCode text(3), DTCCode text(6), Section text(22), Subdivision text(14), Division text(6), Circle text(6),
      Zone text(6), SAPFunctionalLocation text(50), SSFacilityIDFK text(50), Enabled integer, ShapeLength text(50), CYMESubstationCode text(5), Town text(30), TG_PHASE text(200), TG_VOLTAGE text(200), TG_CONNECTIONSTATE text(200), Length text(200), TG_EQUIPMENTID text(200)
AttributeCreator_8
    ATTR_TABLE:
      SET_TO ConnectionStatus = @Value(TG_CONNECTIONSTATE)
      SET_TO LineCableID = @Value(TG_EQUIPMENTID)
      SET_TO SectionID = @Value(GISID)
      SET_TO DeviceNumber = @Value(GISID)
    -> TGLINE_OVERHEADLINE (writer MDB_ADO_1)
Note: AttributeCreator_3 : Input
Junction_20
    -> Junction_21

Bookmark: New Bookmark
Junction_15
    -> AttributeCreator_9
Junction_17
    -> AttributeCreator_9
AttributeCreator_9: Junction
    -> CABLE_Feedername
    -> CABLE_Section
    -> CABLE_Section_2
    -> CABLE_Section_3
    -> CABLE_Section_4
CABLE_Section_4: AttributeCreator
    ATTR_TABLE:
      SET_TO DeviceNumber = @Value(GISID)
      SET_TO DeviceType = 1
      SET_TO DataId = SUBDIVISION
      SET_TO DataType = 8
      SET_TO DataValue = @Value(Subdivision)
    -> AttributeCreator_3
CABLE_Section_3: AttributeCreator
    ATTR_TABLE:
      SET_TO DeviceNumber = @Value(GISID)
      SET_TO DeviceType = 1
      SET_TO DataId = CIRCLE
      SET_TO DataType = 8
      SET_TO DataValue = @Value(Circle)
    -> AttributeCreator_3
CABLE_Section_2: AttributeCreator
    ATTR_TABLE:
      SET_TO DeviceNumber = @Value(GISID)
      SET_TO DeviceType = 1
      SET_TO DataId = TOWN
      SET_TO DataType = 8
      SET_TO DataValue = @Value(Town)
    -> AttributeCreator_3
CABLE_Feedername: AttributeCreator
    ATTR_TABLE:
      SET_TO DeviceNumber = @Value(GISID)
      SET_TO DeviceType = 1
      SET_TO DataId = FEEDERNAME
      SET_TO DataType = 8
      SET_TO DataValue = @Value(FeederName)
    -> AttributeCreator_3
CABLE_Section: AttributeCreator
    ATTR_TABLE:
      SET_TO DeviceNumber = @Value(GISID)
      SET_TO DeviceType = 1
      SET_TO DataId = SECTION
      SET_TO DataType = 8
      SET_TO DataValue = @Value(Section)
    -> AttributeCreator_3
Junction_19
    -> AttributeCreator_10
Junction_21
    -> AttributeCreator_10
AttributeCreator_10: Junction
    -> CONDUCTOR_Feedername
    -> CONDUCTOR_Section
    -> CONDUCTOR_Feedername_2
    -> CONDUCTOR_Section_6
    -> CONDUCTOR_Section_5
CONDUCTOR_Section_6: AttributeCreator
    ATTR_TABLE:
      SET_TO DeviceNumber = @Value(GISID)
      SET_TO DeviceType = 2
      SET_TO DataId = SUBDIVISION
      SET_TO DataType = 8
      SET_TO DataValue = @Value(Subdivision)
    -> AttributeCreator_3
CONDUCTOR_Section_5: AttributeCreator
    ATTR_TABLE:
      SET_TO DeviceNumber = @Value(GISID)
      SET_TO DeviceType = 2
      SET_TO DataId = CIRCLE
      SET_TO DataType = 8
      SET_TO DataValue = @Value(Circle)
    -> AttributeCreator_3
CONDUCTOR_Feedername_2: AttributeCreator
    ATTR_TABLE:
      SET_TO DeviceNumber = @Value(GISID)
      SET_TO DeviceType = 2
      SET_TO DataId = TOWN
      SET_TO DataType = 8
      SET_TO DataValue = @Value(Town)
    -> AttributeCreator_3
CONDUCTOR_Feedername: AttributeCreator
    ATTR_TABLE:
      SET_TO DeviceNumber = @Value(GISID)
      SET_TO DeviceType = 2
      SET_TO DataId = FEEDERNAME
      SET_TO DataType = 8
      SET_TO DataValue = @Value(FeederName)
    -> AttributeCreator_3
CONDUCTOR_Section: AttributeCreator
    ATTR_TABLE:
      SET_TO DeviceNumber = @Value(GISID)
      SET_TO DeviceType = 2
      SET_TO DataId = SECTION
      SET_TO DataType = 8
      SET_TO DataValue = @Value(Section)
    -> AttributeCreator_3
AttributeCreator_3: Junction
    -> TGUDD_DEVICEUDD (writer MDB_ADO_1)
AttributeCreator
    ATTR_TABLE:
      SET_TO SectionId = @Value(GISID)
      SET_TO DataId = FEEDERNAME
      SET_TO DataType = 8
      SET_TO DataValue = @Value(FeederName)
    -> TGUDD_SECTIONUDD (writer MDB_ADO_1)
AttributeCreator_4
    ATTR_TABLE:
      SET_TO SectionId = @Value(GISID)
      SET_TO DataId = SECTION
      SET_TO DataType = 8
      SET_TO DataValue = @Value(Section)
    -> TGUDD_SECTIONUDD (writer MDB_ADO_1)
TGUDD_SECTIONUDD (writer MDB_ADO_1)
    attributes: SectionId text(50), DataId text(200), DataType text(200), DataValue text(200)

Bookmark: DISTRIBUTION TRANSFORMER
AttributeRemover_6
    REMOVE_ATTRS = AdoptedTap,FEEDERINFO,SurveyorRemark,ManufacturingYear,LastMaintenanceDate,MaximumDemand,SerialNumber,TransformerWeight,MinimumTap,Cost,CustomerClassCode,MMELECTRICTRACEWEIGHT,DTCType,CompactType,NeutralEarthing,Make,WorkOrderID,PercentageLoading,LifeSpan,SAPID,FacilityID,LoadTapChangerIndicator,EAEquipment,FeederID2,MagnetizingCurrent,NoLoadLoss,HighSideCurrentRating,LowSideCurrentRating,created_user,last_edited_user,CSPType,LTProtection,HTProtection,CopperLoss,last_edited_date,MaximumTap,TotalLoad,TertiaryVoltage,Warranty,Earthing,TotalLoss,ConsumptionType,StarRating,OilQuantity,TemperatureRisingOil,JobNumber,ConsumerCount,TapLocation,created_date,Ownership,TemperatureRisingWDG
    -> AVM_DT_P
AVM_DT_P: AttributeValueMapper
    DEFAULT_VALUE = 0
    VAL_ATTR = TG_PHASE
    LUT = 1,1,2,1,3,2,4,1,5,2,6,2,7,3
    SRC = Phasedesignation
    DIRECTION = Forward (Source To Destination)
    -> AVM_DT_HS_V
AVM_DT_HS_V: AttributeValueMapper
    DEFAULT_VALUE = KV
    VAL_ATTR = TG_HighSideVoltage
    LUT = 340,11,360,22,380,33,80,66,90,100,110,132,150,220,260,400,120,0.11,160,0.24,210,0.43
    SRC = HighSideVoltage
    DIRECTION = Forward (Source To Destination)
    -> AVM_DT_LS_V
AVM_DT_LS_V: AttributeValueMapper
    DEFAULT_VALUE = KV
    VAL_ATTR = TG_LowSideVoltage
    LUT = 340,11,360,22,380,33,80,66,90,100,110,132,150,220,260,400,120,0.11,160,0.24,210,0.43
    SRC = LowSideVoltage
    DIRECTION = Forward (Source To Destination)
    -> AVM_DT_COOLINGTYPE
AVM_DT_COOLINGTYPE: AttributeValueMapper
    VAL_ATTR = TG_COOLINGTYPE
    LUT = 1,DRY,2,OIL,999,OTHER
    SRC = CoolingType
    DIRECTION = Forward (Source To Destination)
    -> StringReplacer_4
StringReplacer_4
    FIND_TEXT = ,
    SRC_ATTRS = FeederName,Name
    CASE = NO
    REGEXP = NO
    NO_MATCH = _FME_NO_OP_
    -> DT_DEVICETYPE
DT_DEVICETYPE: AttributeCreator
    ATTR_TABLE = SET_TO DEVICETYPE = 5
    -> AVM_DT_CONNECTIONSTATE
AVM_DT_CONNECTIONSTATE: AttributeValueMapper
    VAL_ATTR = TG_CONNECTIONSTATE
    LUT = 1,0,2,1
    SRC = ConnectionState
    DIRECTION = Forward (Source To Destination)
    -> AVM_DT_CONNECTIONSTATE_2
AVM_DT_CONNECTIONSTATE_2: AttributeValueMapper
    VAL_ATTR = TG_TransformerMounting
    LUT = Platform Mounted,PM,Double Pole,DP,Single Pole,SP
    SRC = TransformerMounting
    DIRECTION = Forward (Source To Destination)
    -> StringConcatenator_5
StringConcatenator_5
    PARM_LINE = @Value(TG_PHASE)P_@Value(TG_HighSideVoltage)/@Value(TG_LowSideVoltage)KV_@Value(CapacityInKVA)KVA_@Value(PercentageImpedance)_@Value(TG_COOLINGTYPE)_@Value(TG_TransformerMounting)
    VAL_ATTR = TG_EQUIPMENTID
    ACTION = Create New Attribute
    -> TGDEVICE_DISTRIBUTIONTRANSFORMER (writer MDB_ADO_1)
    -> TGDTAG_DEVICETAG (writer MDB_ADO_1)
    -> GIS_DT (writer MDB_ADO_1)
    -> AttributeCreator_13

Bookmark: New Bookmark
AttributeCreator_13: Junction
    -> DT_Feedername_3
    -> DT_Feedername_2
    -> CONDUCTOR_Section_2
    -> CONDUCTOR_Section_3
    -> CONDUCTOR_Section_4
    -> CONDUCTOR_Section_7
CONDUCTOR_Section_4: AttributeCreator
    ATTR_TABLE:
      SET_TO DeviceNumber = @Value(GISID)
      SET_TO DeviceType = 5
      SET_TO DataId = SUBDIVISION
      SET_TO DataType = 8
      SET_TO DataValue = @Value(Subdivision)
    -> AttributeCreator_14
CONDUCTOR_Section_3: AttributeCreator
    ATTR_TABLE:
      SET_TO DeviceNumber = @Value(GISID)
      SET_TO DeviceType = 5
      SET_TO DataId = CIRCLE
      SET_TO DataType = 8
      SET_TO DataValue = @Value(Circle)
    -> AttributeCreator_14
CONDUCTOR_Section_7: AttributeCreator
    ATTR_TABLE:
      SET_TO DeviceNumber = @Value(GISID)
      SET_TO DeviceType = 5
      SET_TO DataId = SECTION
      SET_TO DataType = 8
      SET_TO DataValue = @Value(Section)
    -> AttributeCreator_14
DT_Feedername_3: AttributeCreator
    ATTR_TABLE:
      SET_TO DeviceNumber = @Value(GISID)
      SET_TO DeviceType = 5
      SET_TO DataId = TOWN
      SET_TO DataType = 8
      SET_TO DataValue = @Value(Town)
    -> AttributeCreator_14
DT_Feedername_2: AttributeCreator
    ATTR_TABLE:
      SET_TO DeviceNumber = @Value(GISID)
      SET_TO DeviceType = 5
      SET_TO DataId = FEEDERNAME
      SET_TO DataType = 8
      SET_TO DataValue = @Value(FeederName)
    -> AttributeCreator_14
CONDUCTOR_Section_2: AttributeCreator
    ATTR_TABLE:
      SET_TO DeviceNumber = @Value(GISID)
      SET_TO DeviceType = 5
      SET_TO DataId = DTCCODE
      SET_TO DataType = 8
      SET_TO DataValue = @Value(DTCCode)
    -> AttributeCreator_14
AttributeCreator_14: Junction
    -> TGUDD_DEVICEUDD (writer MDB_ADO_1)

Bookmark: CYME SOURCE
Note: apdrp_fm.SWITCHGEAR
Junction_9
    -> FeatureMerger_4 [REQUESTOR]
Note: CYMESECTION : Output_node
Junction_11
    -> FeatureMerger_5 [REQUESTOR]
dbo.TG_FEEDERLIST (reader MSSQL_ADO_1)
    attributes: Circle varchar(50), Division varchar(50), Subdivision varchar(50), Name varchar(250), SubstationCode varchar(10), PrimaryVoltage varchar(20), SecondaryVoltage varchar(20), TotalCapacityInMVA float, MaximumDemand varchar(10), FeederName varchar(50), FeederId varchar(40), GISID varchar(50), SwitchGearObjid integer, SubType smallint, Cheched char(20), Town char(20), Section char(50)
    -> StringConcatenator_16
StringConcatenator_16
    PARM_LINE = @Value(SubstationCode)-@Value(Name)
    VAL_ATTR = TG_Subcode_SubName
    ACTION = Create New Attribute
    -> StringReplacer_5
StringReplacer_5
    FIND_TEXT = KV
    SRC_ATTRS = SecondaryVoltage
    CASE = NO
    REGEXP = NO
    NO_MATCH = _FME_NO_OP_
    -> AttributeCreator_7
AttributeCreator_7
    ATTR_TABLE:
      SET_TO Group3 = @Value(Division)
      SET_TO Group2 = @Value(Section)
      SET_TO TagText = @Value(Circle)
      SET_TO Name = @Value(TG_Subcode_SubName)
    -> FeatureMerger_2 [SUPPLIER]
CIRCUITSOURCE (reader SDE30_2)
    attributes: OBJECTID integer, FeederID char(12), FeederID2 char(12), FEEDERINFO integer, SubstationName char(50), SubstationID char(5), SwitchGearObjID integer, FeederName char(50), FeederSourceInfo integer, FeederCode char(3), WorkOrderID char(50), ToSubstationID char(5)
    -> CIRCUITSOURCE [INPUT_CIRCUITSOURCE]
CIRCUITSOURCE: CYMESOURCE
    WORKORDERID = @Value(WorkOrderID)
    FEEDERID = @Value(FeederID)
    SUBSTATIONID = @Value(SubstationID)
    FEEDERID2 = @Value(FeederID2)
    FEEDERNAME = @Value(FeederName)
    FEEDERSOURCEINFO = @Value(FeederSourceInfo)
    OBJECTID = @Value(OBJECTID)
    TOSUBSTATIONID = @Value(ToSubstationID)
    FEEDERINFO = @Value(FEEDERINFO)
    SWITCHGEAROBJID = @Value(SwitchGearObjID)
    -> AttributeCopier
AttributeCopier
    ATTR_TABLE = COPY FeederId > NetworkID
    -> StringConcatenator_10
    -> FeatureMerger_4 [SUPPLIER]
FeatureMerger_4
    ATTR_ACCUM_MODE = Merge Supplier
    PROCESS_DUPS = No
    MERGE_TYPE = Attributes Only
    SUPPLIERS_FIRST = No
    JOIN_KEYS = @Value(OBJECTID) @Value(SwitchGearObjID) AUTO
    IGNORE_NULLS = No
    REJECT_NULL_MISSING_KEYS = No
    ATTR_CONFLICT_RES = Use Requestor
    MERGED -> FeatureMerger_5 [SUPPLIER]
FeatureMerger_5
    ATTR_ACCUM_MODE = Merge Supplier
    PROCESS_DUPS = No
    MERGE_TYPE = Attributes Only
    SUPPLIERS_FIRST = No
    JOIN_KEYS = @Value(GISID) @Value(GISID) AUTO
    IGNORE_NULLS = No
    REJECT_NULL_MISSING_KEYS = No
    ATTR_CONFLICT_RES = Use Requestor
    MERGED -> AttributeCreator_2
AttributeCreator_2
    ATTR_TABLE = SET_TO NodeID = @Value(NodeId)
    -> FeatureMerger_2 [REQUESTOR]
FeatureMerger_2
    ATTR_ACCUM_MODE = Merge Supplier
    PROCESS_DUPS = No
    MERGE_TYPE = Attributes Only
    SUPPLIERS_FIRST = No
    JOIN_KEYS = @Value(FeederId) @Value(FeederId) AUTO
    IGNORE_NULLS = No
    REJECT_NULL_MISSING_KEYS = No
    ATTR_CONFLICT_RES = Use Requestor
    MERGED -> TGSOURCE_SOURCE (writer MDB_ADO_1)
    MERGED -> TGSOURCE_EQUIVALENT (writer MDB_ADO_1)
    MERGED -> TGSOURCE_HEADNODES (writer MDB_ADO_1)
    MERGED -> TGSOURCE_LOADEQUIVALENT (writer MDB_ADO_1)
    MERGED -> TGFEEDER_FORMAT_FEEDER (writer MDB_ADO_1)
    MERGED -> DynamicProtectiveDevice (writer MDB_ADO_1)
    MERGED -> AttributeCreator_6
    MERGED -> AttributeCreator_5
    MERGED -> AVM_FEEDERLIST_PRIV_5
    <REJECTED> -> Erro9898 (writer MDB_ADO_1)
AttributeCreator_5
    ATTR_TABLE:
      SET_TO NetworkId = @Value(NetworkID)
      SET_TO DataId = FEEDERNAME
      SET_TO DataType = 8
      SET_TO DataValue = @Value(FeederName)
    -> TGUDD_NETWORKUDD (writer MDB_ADO_1)
AttributeCreator_6
    ATTR_TABLE:
      SET_TO NetworkId = @Value(NetworkID)
      SET_TO DataId = SECTION
      SET_TO DataType = 8
      SET_TO DataValue = @Value(Section)
    -> TGUDD_NETWORKUDD (writer MDB_ADO_1)
TGSOURCE_HEADNODES (writer MDB_ADO_1)
    attributes: NodeID text(20), NetworkID text(100), ConnectorIndex text(20), StructureID text(100), HarmonicEnveloppe text(20), EquivalentSourceConfiguration long, EquivalentSourceSinglePhaseCT text(50), EquivSourceCenterTapPhase long, BackgroundHarmonicVoltage text(50)
AVM_FEEDERLIST_PRIV_5: AttributeValueMapper
    VAL_ATTR = Town
    LUT = 01,ANGUL,02,BHUBANESWAR,03,CUTTACK,04,DHENKANAL,05,JAGATSINGHAPUR,06,JATNI,07,KENDRAPARA,08,KHORDHA,09,PARADEEP,10,PATTAMUNDAI,11,PURI,12,TALCHER
    SRC = Town
    DIRECTION = Forward (Source To Destination)
    -> AttributeCreator_12
AttributeCreator_12
    ATTR_TABLE:
      SET_TO NetworkId = @Value(NetworkID)
      SET_TO DataId = TOWN
      SET_TO DataType = 8
      SET_TO DataValue = @Value(Town)
    -> TGUDD_NETWORKUDD (writer MDB_ADO_1)
TGUDD_NETWORKUDD (writer MDB_ADO_1)
    attributes: NetworkId text(50), DataId text(200), DataType text(200), DataValue text(200)
TGSOURCE_SOURCE (writer MDB_ADO_1)
    attributes: SourceID text(100), DeviceNumber text(100), NodeID text(100), NetworkID text(100), OperatingVoltageA text(100), OperatingVoltageB text(100), OperatingVoltageC text(100), SinglePhaseCenterTap long, CenterTapPhase text(50)
TGSOURCE_EQUIVALENT (writer MDB_ADO_1)
    attributes: NodeID text(20), LoadModelName text(20), Voltage text(40), OperatingAngle1 text(20), OperatingAngle2 long, OperatingAngle3 text(50), PositiveSequenceResistance long, PositiveSequenceReactance long, NegativeSequenceResistance long, NegativeSequenceReactance long, ZeroSequenceResistance long, ZeroSequenceReactance text(50), OperatingVoltage1 text(50), OperatingVoltage2 text(50), OperatingVoltage3 text(50), BaseMVA text(50), ImpedanceUnit text(50)
TGSOURCE_LOADEQUIVALENT (writer MDB_ADO_1)
    attributes: NodeID text(20), LoadModelName text(20), Format text(40), Value1A text(20), Value1B long, Value1C text(50), Value2A long, Value2B long, Value2C long, ValueSinglePhaseCT11 long, ValueSinglePhaseCT12 long, ValueSinglePhaseCT21 text(50), ValueSinglePhaseCT22 text(50)
TGFEEDER_FORMAT_FEEDER (writer MDB_ADO_1)
    attributes: NetworkID text(200), HeadNodeID text(200), CoordSet text(200), Year text(200), Description text(200), Color text(200), LoadFactor text(200), LossLoadFactorK text(200), Group1 text(200), Group2 text(200), Group3 text(200), TagText text(200), TagProperties text(200), TagDeltaX text(200), TagDeltaY text(200), TagAngle text(200), TagAlignment text(200), TagBorder text(200), TagBackground text(200), TagTextColor text(200), TagBorderColor text(200), TagBackgroundColor text(200), TagLocation text(200), TagFont text(200), TagTextSize text(200), TagOffset text(200), Version text(200), EnvironmentID text(200)
Erro9898 (writer MDB_ADO_1)
    attributes: NodeID text(200)
DynamicProtectiveDevice (writer MDB_ADO_1)
    attributes: FeederId text(20), FeederName text(40), SubstationName text(20), GISID text(20)
StringConcatenator_10
    PARM_LINE = Node_@Value(FeederId)
    VAL_ATTR = NodeID_NotinUse
    ACTION = Create New Attribute

Bookmark: DEVICE
AttributeRemover_5
    REMOVE_ATTRS = AuxiliarySupply,AncillaryRole,created_date,ManufacturingYear,FeederID2,last_edited_date,CTPTCombined,WorkOrderID,Cost,MMELECTRICTRACEWEIGHT,SAPID,SymmetricalBreakingCurrent,FEEDERINFO,created_user,Warranty,EAEquipment,SerialNumber,Mechanism,last_edited_user,LastMaintenanceDate
    -> StringConcatenator_11
StringConcatenator_11
    PARM_LINE = @Value(NormalPositionB)@Value(NormalPositionR)@Value(NormalPositionY)
    VAL_ATTR = TG_NORMALPOSITION
    ACTION = Create New Attribute
    -> AVM_CIRCUITBREAKER_V_3
AVM_CIRCUITBREAKER_V_3: AttributeValueMapper
    DEFAULT_VALUE = NONE
    VAL_ATTR = ClosedPhase
    LUT = 111,ABC,110,AB,101,AC,011,BC,100,A,010,B,001,C
    SRC = TG_NORMALPOSITION
    DIRECTION = Forward (Source To Destination)
    -> AVM_CIRCUITBREAKER_P
AVM_CIRCUITBREAKER_P: AttributeValueMapper
    DEFAULT_VALUE = 0
    VAL_ATTR = TG_PHASE
    LUT = 1,1,2,1,3,2,4,1,5,2,6,2,7,3
    SRC = Phasedesignation
    DIRECTION = Forward (Source To Destination)
    -> AVM_CIRCUITBREAKER_V
AVM_CIRCUITBREAKER_V: AttributeValueMapper
    DEFAULT_VALUE = KV
    VAL_ATTR = TG_Voltage
    LUT = 340,11KV,360,22KV,380,33KV,80,66KV,90,100KV,110,132KV,150,220KV,260,400KV,120,0.11KV,160,0.24KV,210,0.43KV
    SRC = Voltage
    DIRECTION = Forward (Source To Destination)
    -> CIRCUITBREAKER_DEVICETYPE
CIRCUITBREAKER_DEVICETYPE: AttributeCreator
    ATTR_TABLE = SET_TO DEVICETYPE = 8
    -> AVM_BREAKER_NORMALSTATUS
AVM_BREAKER_NORMALSTATUS: AttributeValueMapper
    VAL_ATTR = TG_NORMALSTATUS
    LUT = 0,1,1,0
    SRC = NormalStatus
    DIRECTION = Forward (Source To Destination)
    -> StringConcatenator_6
StringConcatenator_6
    PARM_LINE = @Value(TG_PHASE)P_@Value(TG_Voltage)_@Value(RatedCurrent)A_@Value(InsulationType)_@Value(Make)
    VAL_ATTR = TG_EQUIPMENTID
    ACTION = Create New Attribute
    -> TGDEVICE_CIRCUITBREAKER (writer MDB_ADO_1)
    -> TGDTAG_DEVICETAG (writer MDB_ADO_1)
    -> GIS_CIRCUITBREAKER (writer MDB_ADO_1)
    -> Junction_24
GIS_CIRCUITBREAKER (writer MDB_ADO_1)
    attributes: DEVICETYPE text(200), OBJECTID long, InstalledLocation integer, LocationID text(50), GISID text(50), NIN text(50), SubType integer, FeederID text(50), FeederName text(50), Phasedesignation integer, Voltage integer, InsulationType text(10), RatedPower text(50), DTCCode text(6), MakingCapacity text(50), OperatingSequence text(50), Make text(50), DateofCommissioning datetime, NormalStatus long, NormalPositionR long, NormalPositionY long, NormalPositionB long, PresentPositionR long, PresentPositionY long, PresentPositionB long, RatedCurrent text(4), FeederCode text(50), EquipmentID long, SAPFunctionalLocation text(50), ConnectionStatus text(50),
      Section text(22), Subdivision text(50), Division text(50), Circle text(50), Zone text(50), SurveyorRemark text(250), LocationCodeX double, LocationCodeY double, RMUFacilityIDFK text(50), PillarFacilityIDFK text(50), StationFacilityIDFK text(50), Enabled integer, CYMESubstationCode text(5), Town text(30), TG_NORMALPOSITION text(200), ClosedPhase text(200), TG_PHASE text(200), TG_Voltage text(200), TG_NORMALSTATUS text(200), TG_EQUIPMENTID text(200)
Note: BREAKERUDD : Input
Junction_24
    -> Junction_25
AttributeRemover_7
    REMOVE_ATTRS = created_user,EAEquipment,SAPID,FeederID2,last_edited_user,created_date,SerialNumber,ManufacturingYear,last_edited_date,LastMaintenanceDate,WorkOrderID,Warranty,MMELECTRICTRACEWEIGHT,SurveyorRemark,FEEDERINFO,Cost,Mechanism
    -> StringConcatenator_12
StringConcatenator_12
    PARM_LINE = @Value(NormalPositionB)@Value(NormalPositionR)@Value(NormalPositionY)
    VAL_ATTR = TG_NORMALPOSITION
    ACTION = Create New Attribute
    -> AVM_CIRCUITBREAKER_V_2
AVM_CIRCUITBREAKER_V_2: AttributeValueMapper
    DEFAULT_VALUE = NONE
    VAL_ATTR = ClosedPhase
    LUT = 111,ABC,110,AB,101,AC,011,BC,100,A,010,B,001,C
    SRC = TG_NORMALPOSITION
    DIRECTION = Forward (Source To Destination)
    -> AVM_SWITCH_P
AVM_SWITCH_P: AttributeValueMapper
    DEFAULT_VALUE = 0
    VAL_ATTR = TG_PHASE
    LUT = 1,1,2,1,3,2,4,1,5,2,6,2,7,3
    SRC = Phasedesignation
    DIRECTION = Forward (Source To Destination)
    -> AVM_SWITCH_V
AVM_SWITCH_V: AttributeValueMapper
    DEFAULT_VALUE = KV
    VAL_ATTR = TG_Voltage
    LUT = 340,11KV,360,22KV,380,33KV,80,66KV,90,100KV,110,132KV,150,220KV,260,400KV,120,0.11KV,160,0.24KV,210,0.43KV
    SRC = Voltage
    DIRECTION = Forward (Source To Destination)
    -> AVM_SWITCH_CURRENTRATING
AVM_SWITCH_CURRENTRATING: AttributeValueMapper
    VAL_ATTR = TG_NORMALREATEDCURRENT
    LUT = 1,200,2,400,3,600,4,800,5,1250,6,2000
    SRC = NormalRatedCurrent
    DIRECTION = Forward (Source To Destination)
    -> SWITCH_DEVICETYPE
SWITCH_DEVICETYPE: AttributeCreator
    ATTR_TABLE = SET_TO DEVICETYPE = 13
    -> AVM_SWITCH_NORMALSTATUS
AVM_SWITCH_NORMALSTATUS: AttributeValueMapper
    VAL_ATTR = TG_NORMALSTATUS
    LUT = 0,1,1,0
    SRC = NormalStatus
    DIRECTION = Forward (Source To Destination)
    -> StringConcatenator_7
StringConcatenator_7
    PARM_LINE = @Value(TG_PHASE)P_@Value(TG_Voltage)_@Value(TG_NORMALREATEDCURRENT)A
    VAL_ATTR = TG_EQUIPMENTID
    ACTION = Create New Attribute
    -> TGDEVICE_SWITCH (writer MDB_ADO_1)
    -> TGDTAG_DEVICETAG (writer MDB_ADO_1)
    -> GIS_SWITCH (writer MDB_ADO_1)
    -> Junction_22
GIS_SWITCH (writer MDB_ADO_1)
    attributes: DEVICETYPE text(200), OBJECTID long, GISID text(50), NIN text(50), SubType integer, InstalledLocation integer, LocationID text(50), FeederID text(50), FeederName text(50), Phasedesignation integer, Voltage integer, NormalStatus long, NormalPositionR long, NormalPositionY long, NormalPositionB long, PresentPositionR long, PresentPositionY long, PresentPositionB long, NormalRatedCurrent integer, ReactiveBreakingCurrent text(50), BreakingCurrent text(10), DTCCode text(6), Make text(50), DateofCommissioning datetime, FeederCode text(50), SAPFunctionalLocation text(50), ConnectionStatus text(12), Section text(22), Subdivision text(50), Division text(50),
      Circle text(50), Zone text(50), LocationCodeX double, LocationCodeY double, SSFacilityIDFK text(50), RMUFacilityIDFK text(50), PillarFacilityIDFK text(50), StationFacilityIDFK text(50), Enabled integer, CYME text(11), CYMESubstationCode text(5), Town text(30), TG_NORMALPOSITION text(200), ClosedPhase text(200), TG_PHASE text(200), TG_Voltage text(200), TG_NORMALREATEDCURRENT text(200), TG_NORMALSTATUS text(200), TG_EQUIPMENTID text(200)
Note: SWITCHUDD : Input
Junction_22
    -> Junction_23
AttributeRemover_8
    REMOVE_ATTRS = created_user,EAEquipment,SAPID,FeederID2,last_edited_user,Class,created_date,last_edited_date,WorkOrderID,MMELECTRICTRACEWEIGHT,SurveyorRemark,FEEDERINFO,Cost
    -> StringConcatenator_13
StringConcatenator_13
    PARM_LINE = @Value(NormalPositionB)@Value(NormalPositionR)@Value(NormalPositionY)
    VAL_ATTR = TG_NORMALPOSITION
    ACTION = Create New Attribute
    -> AVM_CIRCUITBREAKER_V_4
AVM_CIRCUITBREAKER_V_4: AttributeValueMapper
    DEFAULT_VALUE = NONE
    VAL_ATTR = ClosedPhase
    LUT = 111,ABC,110,AB,101,AC,011,BC,100,A,010,B,001,C
    SRC = TG_NORMALPOSITION
    DIRECTION = Forward (Source To Destination)
    -> AVM_FUSE_P
AVM_FUSE_P: AttributeValueMapper
    DEFAULT_VALUE = 0
    VAL_ATTR = TG_PHASE
    LUT = 1,1,2,1,3,2,4,1,5,2,6,2,7,3
    SRC = Phasedesignation
    DIRECTION = Forward (Source To Destination)
    -> AVM_FUSE_V
AVM_FUSE_V: AttributeValueMapper
    DEFAULT_VALUE = KV
    VAL_ATTR = TG_Voltage
    LUT = 340,11KV,360,22KV,380,33KV,80,66KV,90,100KV,110,132KV,150,220KV,260,400KV,120,0.11KV,160,0.24KV,210,0.43KV
    SRC = Voltage
    DIRECTION = Forward (Source To Destination)
    -> AVM_FUSE_TYPE
AVM_FUSE_TYPE: AttributeValueMapper
    VAL_ATTR = TG_TYPE
    LUT = 1,DROP_OUT,2,HORN_GAP,3,HRC,4,CARTRIDGE,5,WIRE,6,KITKAT_FUSE,7,OTHER
    SRC = Type
    DIRECTION = Forward (Source To Destination)
    -> FUSE_DEVICETYPE
FUSE_DEVICETYPE: AttributeCreator
    ATTR_TABLE = SET_TO DEVICETYPE = 14
    -> AVM_FUSE_NORMALSTATUS
AVM_FUSE_NORMALSTATUS: AttributeValueMapper
    VAL_ATTR = TG_NORMALSTATUS
    LUT = 0,1,1,0
    SRC = NormalStatus
    DIRECTION = Forward (Source To Destination)
    -> StringConcatenator_8
StringConcatenator_8
    PARM_LINE = @Value(TG_PHASE)P_@Value(TG_Voltage)_@Value(Rating)A_@Value(TG_TYPE)
    VAL_ATTR = TG_EQUIPMENTID
    ACTION = Create New Attribute
    -> TGDEVICE_FUSE (writer MDB_ADO_1)
    -> TGDTAG_DEVICETAG (writer MDB_ADO_1)
    -> GIS_FUSE (writer MDB_ADO_1)
    -> Junction_26
GIS_FUSE (writer MDB_ADO_1)
    attributes: DEVICETYPE text(200), OBJECTID long, InstalledLocation integer, LocationID text(50), Name text(250), GISID text(50), NIN text(50), FeederID text(50), FeederName text(50), Voltage integer, Type integer, Phasedesignation integer, NormalStatus long, NormalPositionR long, NormalPositionY long, NormalPositionB long, PresentPositionR long, PresentPositionY long, PresentPositionB long, FaultCurrent integer, DTCCode text(6), ConnectionStatus text(12), FeederCode text(50), Section text(22), Subdivision text(50), Division text(50), Circle text(50), Zone text(50), LocationCodeX double, LocationCodeY double,
      SAPFunctionalLocation text(50), StationFacilityIDFK text(50), RMUFacilityIDFK text(50), SSFacilityIDFK text(50), PillarFacilityIDFK text(50), Enabled integer, Rating double, CYMESubstationCode text(5), LTCircuitCode text(1), Town text(30), TG_NORMALPOSITION text(200), ClosedPhase text(200), TG_PHASE text(200), TG_Voltage text(200), TG_TYPE text(200), TG_NORMALSTATUS text(200), TG_EQUIPMENTID text(200)
Note: FUSEUDD : Input
Junction_26
    -> Junction_27
AttributeRemover_9
    REMOVE_ATTRS = Cost,LocationCode_X,EAEquipment,SerialNumber,WorkOrderID,FeederID2,DTCCodeDetails,last_edited_date,created_date,created_user,FEEDERINFO,LocationCode_Y,MMELECTRICTRACEWEIGHT,last_edited_user,SAPID,Section
    -> AVM_SHUNTCAPACITOR_P
AVM_SHUNTCAPACITOR_P: AttributeValueMapper
    DEFAULT_VALUE = 0
    VAL_ATTR = TG_PHASE
    LUT = 1,1,2,1,3,2,4,1,5,2,6,2,7,3
    SRC = Phasedesignation
    DIRECTION = Forward (Source To Destination)
    -> AVM_SHUNTCAPACITOR_V
AVM_SHUNTCAPACITOR_V: AttributeValueMapper
    DEFAULT_VALUE = KV
    VAL_ATTR = TG_Voltage
    LUT = 340,11KV,360,22KV,380,33KV,80,66KV,90,100KV,110,132KV,150,220KV,260,400KV,120,0.11KV,160,0.24KV,210,0.43KV
    SRC = Voltage
    DIRECTION = Forward (Source To Destination)
    -> SHUNTCAPACITOR_DEVICETYPE
SHUNTCAPACITOR_DEVICETYPE: AttributeCreator
    ATTR_TABLE = SET_TO DEVICETYPE = 17
    -> StringConcatenator_9
StringConcatenator_9
    PARM_LINE = @Value(TG_PHASE)P_@Value(TG_Voltage)_@Value(CapacityInKVAR)
    VAL_ATTR = TG_EQUIPMENTID
    ACTION = Create New Attribute
    -> TGDEVICE_SHUNTCAPACITOR (writer MDB_ADO_1)
    -> TGDTAG_DEVICETAG (writer MDB_ADO_1)
    -> GIS_SHUNTCAPACITOR (writer MDB_ADO_1)
    -> Junction_28
GIS_SHUNTCAPACITOR (writer MDB_ADO_1)
    attributes: DEVICETYPE text(200), OBJECTID long, Name text(250), GISID text(50), NIN text(50), FeederID text(50), FeederName text(50), InstalledLocation integer, Voltage integer, Phasedesignation integer, CapacityInKVAR double, VectorGroup text(30), DTCCode text(6), Make text(50), Setting text(50), FeederCode text(50), ConnectionStatus text(12), MultiplyingFactor double, Subdivision text(50), Division text(50), Circle text(50), Zone text(50), SurveyorRemark text(250), LocationCodeX double, LocationCodeY double, EquipmentIDFK long, SAPFunctionalLocation text(50), StationFacilityIDFK text(50), Enabled integer, ShuntReactance double,
      CYMESubstationCode text(50), Town text(30), TG_PHASE text(200), TG_Voltage text(200), TG_EQUIPMENTID text(200)
Junction_28
    -> Junction_29
AVM_FUSE_NORMALSTATUS_2: AttributeValueMapper
    VAL_ATTR = TG_NORMALSTATUS
    LUT = 0,1,1,0
    SRC = NormalStatus
    DIRECTION = Forward (Source To Destination)

Bookmark: BREAKER UDD
Junction_25
    -> BREAKERUDD
    -> CONDUCTOR_Section_9
    -> CONDUCTOR_Section_8
    -> CONDUCTOR_Section_10
    -> DT_Feedername_4
CONDUCTOR_Section_9: AttributeCreator
    ATTR_TABLE:
      SET_TO DeviceNumber = @Value(GISID)
      SET_TO DeviceType = 8
      SET_TO DataId = SUBDIVISION
      SET_TO DataType = 8
      SET_TO DataValue = @Value(Subdivision)
    -> AttributeCreator_15
CONDUCTOR_Section_8: AttributeCreator
    ATTR_TABLE:
      SET_TO DeviceNumber = @Value(GISID)
      SET_TO DeviceType = 8
      SET_TO DataId = CIRCLE
      SET_TO DataType = 8
      SET_TO DataValue = @Value(Circle)
    -> AttributeCreator_15
CONDUCTOR_Section_10: AttributeCreator
    ATTR_TABLE:
      SET_TO DeviceNumber = @Value(GISID)
      SET_TO DeviceType = 8
      SET_TO DataId = SECTION
      SET_TO DataType = 8
      SET_TO DataValue = @Value(Section)
    -> AttributeCreator_15
DT_Feedername_4: AttributeCreator
    ATTR_TABLE:
      SET_TO DeviceNumber = @Value(GISID)
      SET_TO DeviceType = 8
      SET_TO DataId = TOWN
      SET_TO DataType = 8
      SET_TO DataValue = @Value(Town)
    -> AttributeCreator_15
BREAKERUDD: AttributeCreator
    ATTR_TABLE:
      SET_TO DeviceNumber = @Value(GISID)
      SET_TO DeviceType = 8
      SET_TO DataId = FEEDERNAME
      SET_TO DataType = 8
      SET_TO DataValue = @Value(FeederName)
    -> AttributeCreator_15
AttributeCreator_15: Junction
    -> TGUDD_DEVICEUDD (writer MDB_ADO_1)

Bookmark: SWITCH UDD
Junction_23
    -> SWITCHUDD
    -> CONDUCTOR_Section_12
    -> CONDUCTOR_Section_11
    -> CONDUCTOR_Section_13
    -> DT_Feedername_5
CONDUCTOR_Section_12: AttributeCreator
    ATTR_TABLE:
      SET_TO DeviceNumber = @Value(GISID)
      SET_TO DeviceType = 13
      SET_TO DataId = SUBDIVISION
      SET_TO DataType = 8
      SET_TO DataValue = @Value(Subdivision)
    -> AttributeCreator_16
CONDUCTOR_Section_11: AttributeCreator
    ATTR_TABLE:
      SET_TO DeviceNumber = @Value(GISID)
      SET_TO DeviceType = 13
      SET_TO DataId = CIRCLE
      SET_TO DataType = 8
      SET_TO DataValue = @Value(Circle)
    -> AttributeCreator_16
CONDUCTOR_Section_13: AttributeCreator
    ATTR_TABLE:
      SET_TO DeviceNumber = @Value(GISID)
      SET_TO DeviceType = 13
      SET_TO DataId = SECTION
      SET_TO DataType = 8
      SET_TO DataValue = @Value(Section)
    -> AttributeCreator_16
DT_Feedername_5: AttributeCreator
    ATTR_TABLE:
      SET_TO DeviceNumber = @Value(GISID)
      SET_TO DeviceType = 13
      SET_TO DataId = TOWN
      SET_TO DataType = 8
      SET_TO DataValue = @Value(Town)
    -> AttributeCreator_16
SWITCHUDD: AttributeCreator
    ATTR_TABLE:
      SET_TO DeviceNumber = @Value(GISID)
      SET_TO DeviceType = 13
      SET_TO DataId = FEEDERNAME
      SET_TO DataType = 8
      SET_TO DataValue = @Value(FeederName)
    -> AttributeCreator_16
AttributeCreator_16: Junction
    -> TGUDD_DEVICEUDD (writer MDB_ADO_1)

Bookmark: SWITCH UDD
Junction_27
    -> FUSEUDD
    -> CONDUCTOR_Section_15
    -> CONDUCTOR_Section_14
    -> CONDUCTOR_Section_16
    -> DT_Feedername_6
CONDUCTOR_Section_15: AttributeCreator
    ATTR_TABLE:
      SET_TO DeviceNumber = @Value(GISID)
      SET_TO DeviceType = 14
      SET_TO DataId = SUBDIVISION
      SET_TO DataType = 8
      SET_TO DataValue = @Value(Subdivision)
    -> AttributeCreator_17
CONDUCTOR_Section_14: AttributeCreator
    ATTR_TABLE:
      SET_TO DeviceNumber = @Value(GISID)
      SET_TO DeviceType = 14
      SET_TO DataId = CIRCLE
      SET_TO DataType = 8
      SET_TO DataValue = @Value(Circle)
    -> AttributeCreator_17
CONDUCTOR_Section_16: AttributeCreator
    ATTR_TABLE:
      SET_TO DeviceNumber = @Value(GISID)
      SET_TO DeviceType = 14
      SET_TO DataId = SECTION
      SET_TO DataType = 8
      SET_TO DataValue = @Value(Section)
    -> AttributeCreator_17
DT_Feedername_6: AttributeCreator
    ATTR_TABLE:
      SET_TO DeviceNumber = @Value(GISID)
      SET_TO DeviceType = 14
      SET_TO DataId = TOWN
      SET_TO DataType = 8
      SET_TO DataValue = @Value(Town)
    -> AttributeCreator_17
FUSEUDD: AttributeCreator
    ATTR_TABLE:
      SET_TO DeviceNumber = @Value(GISID)
      SET_TO DeviceType = 14
      SET_TO DataId = FEEDERNAME
      SET_TO DataType = 8
      SET_TO DataValue = @Value(FeederName)
    -> AttributeCreator_17

Bookmark: New Bookmark
AttributeCreator_17: Junction
    -> TGUDD_DEVICEUDD (writer MDB_ADO_1)
Junction_29
    -> SHUNTCAPACITORUDD
SHUNTCAPACITORUDD: AttributeCreator
    ATTR_TABLE:
      SET_TO DeviceNumber = @Value(GISID)
      SET_TO DeviceType = 17
      SET_TO DataId = FEEDERNAME
      SET_TO DataType = 8
      SET_TO DataValue = @Value(FeederName)
    -> TGUDD_DEVICEUDD (writer MDB_ADO_1)
TGUDD_DEVICEUDD (writer MDB_ADO_1)
    attributes: DeviceNumber text(50), DeviceType text(20), DataId text(200), DataType text(200), DataValue text(200)

Bookmark: CYME DEVICE TAG
TGDTAG_DEVICETAG (writer MDB_ADO_1)
    attributes: DeviceNumber text(200), DeviceType text(200), TagText text(200), TagProperties text(200), TagDeltaX text(200), TagDeltaY text(200), TagAngle text(200), TagAlignment text(200), TagBorder text(200), TagBackground text(200), TagTextColor text(200), TagBorderColor text(200), TagBackgroundColor text(200), TagLocation text(200), TagFont text(200), TagTextSize text(200), TagOffset text(200)

Bookmark: BUSBAR ( LINE )
BUSBAR (reader SDE30_2)
    attributes: OBJECTID integer, InstalledLocation smallint, LocationID char(50), GISID char(50), NIN char(50), SubType smallint, FeederID char(12), FeederID2 char(12), FeederName char(50), Voltage smallint, Phasedesignation smallint, Material char(9), CurrentRating smallint, TracingStatus integer, RatedAmps char(50), Class smallint, Cost char(10), EAEquipment char(50), SAPID char(50), WorkOrderID char(50), SurveyorRemark char(50), FeederCode char(3), Section char(22), Subdivision char(14), Division char(6), Circle char(6), Zone char(6), ConnectionStatus char(12), FEEDERINFO integer, FacilityID char(20),
      SAPFunctionalLocation char(50), SGEquipmentIDFK integer, StationFacilityIDFK char(50), RMUFacilityIDFK char(50), PillarFacilityIDFK char(50), CODE char(14), MMELECTRICTRACEWEIGHT integer, created_user char(255), created_date date, last_edited_user char(255), last_edited_date date, Enabled smallint, ShapeLength char(50), CYMESubstationCode char(5), Town char(30), SHAPE_STLength__ double
    -> GIS_BUSBAR (writer MDB_ADO_1)
    -> PointOnLineOverlayer [LINE]
GIS_BUSBAR (writer MDB_ADO_1)
    attributes: OBJECTID long, InstalledLocation integer, LocationID text(50), GISID text(50), NIN text(50), SubType integer, FeederID text(50), FeederID2 text(50), FeederName text(50), Voltage integer, Phasedesignation integer, Material text(50), CurrentRating integer, TracingStatus long, RatedAmps text(50), Class integer, Cost text(50), EAEquipment text(50), SAPID text(50), WorkOrderID text(50), SurveyorRemark text(250), FeederCode text(50), Section text(50), Subdivision text(50), Division text(50), Circle text(50), Zone text(50), ConnectionStatus text(12), FEEDERINFO long, FacilityID text(20),
      SAPFunctionalLocation text(50), SGEquipmentIDFK long, StationFacilityIDFK text(50), RMUFacilityIDFK text(50), PillarFacilityIDFK text(50), CODE text(14), MMELECTRICTRACEWEIGHT long, created_user text(255), created_date datetime, last_edited_user text(255), last_edited_date datetime, Enabled integer, ShapeLength text(50), CYMESubstationCode text(5), Town text(30), SHAPE_STLength__ double

Bookmark: SERVICE POINT HT & LT ( POINT )
HTSERVICEPOINT (reader SDE30_2)
    attributes: OBJECTID integer, Name char(250), ConsumerNumber char(12), GISID char(50), NIN char(50), FeederID char(12), FeederID2 char(12), FeederName char(50), SubstationCode char(5), SubstationName char(50), Voltage smallint, Phasedesignation smallint, ConsumptionType char(50), FagEnd char(3), ConsumerCount char(4), FeederCode char(3), ConnectedToPole char(19), BuildingID char(50), MapID char(50), Cost char(10), EAEquipment char(50), SAPID char(50), WorkOrderID char(50), SurveyorRemark char(250), Section char(22), Subdivision char(14), Division char(6), Circle char(6), Zone char(6), LocationCodeX double,
      LocationCodeY double, MMELECTRICTRACEWEIGHT integer, FEEDERINFO integer, DTEquipmentIDFK integer, SAPFunctionalLocation char(12), ConnectionStatus char(12), created_user char(255), created_date date, last_edited_user char(255), last_edited_date date, Enabled smallint, SanctionedLoad float, CYMESubstationCode char(5), Town char(50)
    -> AttributeRemover_11
    -> CYMESECTION
AttributeRemover_11
    REMOVE_ATTRS = EAEquipment,last_edited_date,LocationCode_X,WorkOrderID,ConsumptionType,Division,FEEDERINFO,Section,FeederID2,FagEnd,OBJECTID,SubstationCode,created_date,SurveyorRemark,Zone,MMELECTRICTRACEWEIGHT,Cost,Subdivision,NIN,MapID,last_edited_user,created_user,Name,LocationCode_Y,SubstationName,SAPID
    -> GIS_HTSERVICEPOINT (writer MDB_ADO_1)
    -> CYMELOAD [SERVICEPOINT]
GIS_HTSERVICEPOINT (writer MDB_ADO_1)
    attributes: ConsumerNumber text(250), GISID text(50), FeederID text(50), FeederName text(50), Voltage integer, Phasedesignation integer, ConsumerCount double, FeederCode text(50), ConnectedToPole text(30), BuildingID text(50), Circle text(50), LocationCodeX double, LocationCodeY double, DTEquipmentIDFK long, SAPFunctionalLocation text(12), ConnectionStatus text(12), Enabled integer, SanctionedLoad double, CYMESubstationCode text(5), Town text(50)
LTSERVICEPOINT (reader SDE30_2)
    attributes: OBJECTID integer, Name char(250), GISID char(50), NIN char(50), FeederID char(12), FeederID2 char(12), FeederName char(50), DTCCode char(6), DTCName char(250), FeederCode char(3), SubstationCode char(5), SubstationName char(50), Voltage smallint, Phasedesignation smallint, ConsumptionType char(50), FagEnd char(3), ConsumerCount char(4), Cost char(10), ConnectedToPole char(19), BuildingID char(50), MapID char(50), Section char(22), Subdivision char(14), Division char(6), Circle char(6), Zone char(6), EAEquipment char(50), SAPID char(50), WorkOrderID char(50), SurveyorRemark char(250),
      ConsumerNumber char(12), ConnectionStatus char(12), SAPFunctionalLocation char(50), LocationCodeX double, LocationCodeY double, MMELECTRICTRACEWEIGHT integer, FEEDERINFO integer, DTEquipmentIDFK integer, created_user char(255), created_date date, last_edited_user char(255), last_edited_date date, Enabled smallint, SanctionedLoad float, CYMESubstationCode char(50), Town char(30)
    -> AttributeRemover_10
    -> CYMESECTION
Note: CYMESECTION : Output_node
Junction_5
    -> CYMELOAD [NODES]
Note: CYMESECTION : Output_Prisec
Junction_4
    -> CYMELOAD [PRISEC]
AttributeRemover_10
    REMOVE_ATTRS = EAEquipment,last_edited_date,LocationCode_X,WorkOrderID,ConsumptionType,DTCCode,Division,FEEDERINFO,Section,FeederID2,FagEnd,OBJECTID,SubstationCode,created_date,SurveyorRemark,Zone,Cost,MMELECTRICTRACEWEIGHT,Subdivision,DTCName,FeederCode,NIN,MapID,last_edited_user,Circle,created_user,Name,FeederName,LocationCode_Y,SubstationName,SanctionedLoad,SAPID
    -> GIS_LTSERVICEPOINT (writer MDB_ADO_1)
    -> CYMELOAD [SERVICEPOINT]
GIS_LTSERVICEPOINT (writer MDB_ADO_1)
    attributes: GISID text(50), FeederID text(50), Voltage integer, Phasedesignation integer, ConsumerCount double, ConnectedToPole text(30), BuildingID text(50), ConsumerNumber text(12), ConnectionStatus text(12), SAPFunctionalLocation text(50), LocationCodeX double, LocationCodeY double, DTEquipmentIDFK long, Enabled integer, CYMESubstationCode text(50), Town text(30)
CYMELOAD
    NORMALPOSITION_C = @Value(NormalPosition_C)
    RATEDCURRENT = @Value(RatedCurrent)
    CABLESIZE = @Value(CableSize)
    TEMPERATURERISINGOIL = @Value(TemperatureRisingOil)
    OILQUANTITY = @Value(OilQuantity)
    NORMALRATEDCURRENT = @Value(NormalRatedCurrent)
    TRANSFORMERMOUNTING = @Value(TransformerMounting)
    EARTHING = @Value(Earthing)
    RATEDAMPS = @Value(RatedAmps)
    EXSTING_CESU_DTC_CODE = @Value(Exsting_Cesu_DTC_Code)
    SUBDIVISION = @Value(Subdivision)
    CONNECTIONSTATE = @Value(ConnectionState)
    CONSUMERCOUNT = @Value(ConsumerCount)
    FROM_GISID = @Value(FROM_GISID)
    PRESENTPOSITION_B = @Value(PresentPosition_B)
    VOLTAGE = @Value(Voltage)
    NAME = @Value(Name)
    _ELEMENT_INDEX = @Value(_element_index)
    SIZE_OF_ADD_CONDUCTOR = @Value(Size_Of_Add_Conductor)
    HIGHSIDEVOLTAGE = @Value(HighSideVoltage)
    CAPACITYINKVAR = @Value(CapacityInKVAR)
    SHUNTREACTANCE = @Value(ShuntReactance)
    SYMMETRICALBREAKINGCURRENT = @Value(SymmetricalBreakingCurrent)
    ARMOURED = @Value(Armoured)
    RATEDPOWER = @Value(RatedPower)
    FAGEND = @Value(FagEnd)
    AUXILIARYSUPPLY = @Value(AuxiliarySupply)
    CTPTCOMBINED = @Value(CTPTCombined)
    DATEOFMANUFACTURING = @Value(DateOfManufacturing)
    TRANSFORMERWEIGHT = @Value(TransformerWeight)
    FEEDERCODE = @Value(FeederCode)
    PHASEDESIGNATION = @Value(Phasedesignation)
    CABLETYPE = @Value(CableType)
    CREATED_USER = @Value(created_user)
    RESISTANCE = @Value(Resistance)
    MAT_OF_ADD_CONDUCTOR = @Value(Mat_Of_Add_Conductor)
    SUBSTATIONNAME = @Value(SubstationName)
    FEEDERINFO = @Value(FEEDERINFO)
    NUMBEROFCORE = @Value(NumberOfCore)
    CONDUCTORSIZE = @Value(ConductorSize)
    CONSUMPTIONTYPE = @Value(ConsumptionType)
    TOTALLOAD = @Value(TotalLoad)
    TRACINGSTATUS = @Value(TracingStatus)
    CSPTYPE = @Value(CSPType)
    OWNERSHIP = @Value(Ownership)
    NIN = @Value(NIN)
    Y = @Value(Y)
    TEMPERATURERISINGWDG = @Value(TemperatureRisingWDG)
    VECTORGROUP = @Value(VectorGroup)
    NEUTRALEARTHING = @Value(NeutralEarthing)
    MMELECTRICTRACEWEIGHT = @Value(MMELECTRICTRACEWEIGHT)
    FEEDERID = @Value(FeederID)
    WARRANTY = @Value(Warranty)
    LTPROTECTION = @Value(LTProtection)
    STARRATING = @Value(StarRating)
    ENABLED = @Value(Enabled)
    JOBNUMBER = @Value(JobNumber)
    NORMALSTATUS = @Value(NormalStatus)
    LAST_EDITED_DATE = @Value(last_edited_date)
    LASTMAINTENANCEDATE = @Value(LastMaintenanceDate)
    CONNECTEDTOPOLE = @Value(ConnectedToPole)
    TOTALLOSS = @Value(TotalLoss)
    DTCTYPE = @Value(DTCType)
    PRESENTPOSITION_R = @Value(PresentPosition_R)
    MULTIPLYINGFACTOR = @Value(MultiplyingFactor)
    CONSUMERNUMBER = @Value(ConsumerNumber)
    FEEDERNAME = @Value(FeederName)
    MECHANISM = @Value(Mechanism)
    NORMALPOSITION_B = @Value(NormalPosition_B)
    _OBJECTID = @Value(_OBJECTID)
    INSULATIONTYPE = @Value(InsulationType)
    LAST_EDITED_USER = @Value(last_edited_user)
    OBJECTID = @Value(OBJECTID)
    SETTING = @Value(Setting)
    ANCILLARYROLE = @Value(AncillaryRole)
    MAPID = @Value(MapID)
    LOWSIDECURRENTRATING = @Value(LowSideCurrentRating)
    SIZE_OF_NEUTRAL_CONDUCTOR = @Value(Size_Of_Neutral_Conductor)
    MAKINGCAPACITY = @Value(MakingCapacity)
    TYPEOFCORE = @Value(TypeOfCore)
    SURVEYORREMARK = @Value(SurveyorRemark)
    PERCENTAGEIMPEDANCE = @Value(PercentageImpedance)
    CUSTOMERCLASSCODE = @Value(CustomerClassCode)
    MAGNETIZINGCURRENT = @Value(MagnetizingCurrent)
    IMPEDANCE = @Value(Impedance)
    SERIALNUMBER = @Value(SerialNumber)
    CONDUCTORTYPE = @Value(ConductorType)
    MAT_OF_NEUTRAL_CONDUCTOR = @Value(Mat_Of_Neutral_Conductor)
    SUBSTATIONCODE = @Value(SubstationCode)
    MAKE = @Value(Make)
    DTCCODEDETAILS = @Value(DTCCodeDetails)
    TYPEOFSUPPORT = @Value(TypeOfSupport)
    DIVISION = @Value(Division)
    LIFESPAN = @Value(LifeSpan)
    SAPID = @Value(SAPID)
    SUBTYPE = @Value(SubType)
    COMPACTTYPE = @Value(CompactType)
    OVERHEADHEIGHT = @Value(OverheadHeight)
    SANCTIONEDLOAD = @Value(SanctionedLoad)
    LOCATIONCODE_Y = @Value(LocationCode_Y)
    TYPE = @Value(Type)
    X = @Value(X)
    CREATED_DATE = @Value(created_date)
    PRESENTPOSITION_Y = @Value(PresentPosition_Y)
    LOCATIONID = @Value(LocationID)
    ADOPTEDTAP = @Value(AdoptedTap)
    FEEDERID2 = @Value(FeederID2)
    NORMALPOSITION_A = @Value(NormalPosition_A)
    MINIMUMTAP = @Value(MinimumTap)
    SHAPE_STLENGTH__ = @Value(SHAPE_STLength__)
    LOCATIONCODE_X = @Value(LocationCode_X)
    NOLOADLOSS = @Value(NoLoadLoss)
    MANUFACTURINGYEAR = @Value(ManufacturingYear)
    TERTIARYVOLTAGE = @Value(TertiaryVoltage)
    FACILITYID = @Value(FacilityID)
    LOWSIDEVOLTAGE = @Value(LowSideVoltage)
    NEUTRALCONDUCTOR = @Value(NeutralConductor)
    MATERIAL = @Value(Material)
    SECTION = @Value(Section)
    COPPERLOSS = @Value(CopperLoss)
    SIZE_OF_ADD_CONDUCTORS = @Value(Size_Of_Add_Conductors)
    DTCNAME = @Value(DTCName)
    DTCCONDITION = @Value(DTCCondition)
    NUMBEROFSTEPS = @Value(NumberOfSteps)
    MAXIMUMDEMAND = @Value(MaximumDemand)
    CONDUCTORMATERIAL = @Value(ConductorMaterial)
    LOADTAPCHANGERINDICATOR = @Value(LoadTapChangerIndicator)
    TAPLOCATION = @Value(TapLocation)
    REACTIVEBREAKINGCURRENT = @Value(ReactiveBreakingCurrent)
    OPERATINGSEQUENCE = @Value(OperatingSequence)
    BUILDINGID = @Value(BuildingID)
    CAPACITYINKVA = @Value(CapacityInKVA)
    CLASS = @Value(Class)
    GISID = @Value(GISID)
    EAEQUIPMENT = @Value(EAEquipment)
    ADDITIONALCONDUCTOR = @Value(AdditionalConductor)
    ZONE = @Value(Zone)
    COST = @Value(Cost)
    MAXIMUMTAP = @Value(MaximumTap)
    TO_GISID = @Value(TO_GISID)
    HIGHSIDECURRENTRATING = @Value(HighSideCurrentRating)
    CIRCLE = @Value(Circle)
    PERCENTAGELOADING = @Value(PercentageLoading)
    COOLINGTYPE = @Value(CoolingType)
    DATEOFCOMMISSIONING = @Value(DateOfCommissioning)
    NUMBEROFCIRCUITS = @Value(NumberOfCircuits)
    DTCCODE = @Value(DTCCode)
    NODEID = @Value(NodeId)
    SWITCHID = @Value(SwitchID)
    BREAKINGCURRENT = @Value(BreakingCurrent)
    NUMBEROFWIRES = @Value(NumberOfWires)
    WEIGHTOFOILL = @Value(WeightOfOill)
    INSTALLEDLOCATION = @Value(InstalledLocation)
    HTPROTECTION = @Value(HTProtection)
    TG_COORDINATES = @Value(TG_Coordinates)
    RATING = @Value(Rating)
    CURRENTRATING = @Value(CurrentRating)
    WORKORDERID = @Value(WorkOrderID)
    NUMBEROFWAYS = @Value(NumberOfWays)
    FAULTCURRENT = @Value(FaultCurrent)
    CONFIGURATION = @Value(Configuration)
    -> TGLOAD_LOADS (writer MDB_ADO_1)
    -> LOADS (writer MDB_ADO_1)
LOADS (writer MDB_ADO_1)
    attributes: SECTIONID text(200), DeviceNumber text(200), LoadType text(50), BuildingID text(50)
TGLOAD_LOADS (writer MDB_ADO_1)
    attributes: SECTIONID text(200), DeviceNumber text(200), DeviceStage text(200), Flags text(50), LoadType text(50), Connection text(200), Location text(200)

Bookmark: SECTION NOT BREAKED
FeatureMerger_3
    ATTR_ACCUM_MODE = Merge Supplier
    PROCESS_DUPS = No
    MERGE_TYPE = Attributes Only
    GROUP_BY = GISID
    SUPPLIERS_FIRST = No
    JOIN_KEYS = @Value(GISID) @Value(GISID) AUTO
    IGNORE_NULLS = No
    REJECT_NULL_MISSING_KEYS = No
    ATTR_CONFLICT_RES = Use Requestor
    MERGED -> FeatureMerger_3_MERGED_-__TempSection_NotBreaked
    <REJECTED> -> TempSection00 (writer MDB_ADO_1)
FeatureMerger_3_MERGED_-__TempSection_NotBreaked: Junction
    -> TempSection_NotBreaked (writer MDB_ADO_1)
    -> FinalSection (writer MDB_ADO_1)
TempSection_NotBreaked (writer MDB_ADO_1)
    attributes: SectionId text(200), FromNodeId text(200), FromNodeIndex text(200), ToNodeId text(200), ToNodeIndex text(200), Phase text(200), ZoneID text(200), SubNetworkId text(200), EnvironmentID text(200)
TempSection00 (writer MDB_ADO_1)
    attributes: SectionId text(200), GISID text(50), X text(200), Y text(200), OBJECTID long, NIN text(50), ToGISID text(50), FromGISID text(50), FeederID text(50), FeederID2 text(50), FeederName text(50), Phasedesignation integer, Voltage integer, NumberofWires integer, ConnectionStatus text(12), TracingStatus long, TypeofSupport text(13), Configuration text(50), ConductorMaterial text(50), ConductorType text(11), ConductorSize text(9), NeutralConductor text(3), MatofNeutralConductor text(9), SizeofNeutralConductor text(9), AdditionalConductor text(3), SizeofAddConductor text(9), MatofAddConductor text(9), RatedCurrent text(50), OverheadHeight text(50), Cost text(50),
      FeederCode text(50), Impedance text(50), DTCCode text(50), Resistance text(50), Section text(50), Subdivision text(50), Division text(50), Circle text(50), Zone text(50), EAEquipment text(50), SAPID text(50), WorkOrderID text(50), SurveyorRemark text(250), MMELECTRICTRACEWEIGHT long, FEEDERINFO long, SAPFunctionalLocation text(50), SSFacilityIDFK text(50), created_user text(255), created_date datetime, last_edited_user text(255), last_edited_date datetime, Enabled integer, ShapeLength text(50), CYMESubstationCode text(5), Town text(30), Name text(250), ConsumerNumber text(250), SubstationCode text(50), SubstationName text(50), ConsumptionType text(50),
      FagEnd text(50), ConsumerCount double, ConnectedToPole text(30), BuildingID text(50), MapID text(50), LocationCodeX double, LocationCodeY double, DTEquipmentIDFK long, SanctionedLoad double, InstalledLocation integer, LocationID text(50), SubType integer, InsulationType text(10), Mechanism integer, AuxiliarySupply text(50), SymmetricalBreakingCurrent text(10), RatedPower text(50), CTPTCombined text(50), MakingCapacity text(50), OperatingSequence text(50), Make text(50), SerialNumber text(50), ManufacturingYear text(50), DateofCommissioning datetime, LastMaintenanceDate datetime, Warranty text(50), AncillaryRole integer, NormalStatus long, NormalPositionR long, NormalPositionY long,
      NormalPositionB long, PresentPositionR long, PresentPositionY long, PresentPositionB long, EquipmentID long, RMUFacilityIDFK text(50), PillarFacilityIDFK text(50), StationFacilityIDFK text(50), DTCName text(50), CapacityInKVAR double, VectorGroup text(50), Setting text(50), MultiplyingFactor double, EquipmentIDFK long, ShuntReactance double, NormalRatedCurrent integer, ReactiveBreakingCurrent text(50), BreakingCurrent text(10), CYME text(11), Type integer, FaultCurrent integer, Class integer, Rating double, LTCircuitCode text(1), NumberofCore integer, NumberofCircuits text(14), CableSize text(30), Armoured text(50), CableType integer, ExstingCESUDTCCode text(10),
      CapacityInKVA integer, PercentageImpedance text(10), HighSideVoltage integer, HTProtection text(50), LTProtection text(20), LowSideVoltage integer, TransformerMounting text(30), DTCondition text(6), TypeofCore text(9), TotalLoss text(50), CustomerClassCode text(20), MaximumTap text(20), MinimumTap text(20), NumberofSteps integer, AdoptedTap text(20), StarRating text(20), CSPType text(20), MaximumDemand text(50), JobNumber text(20), DateofManufacturing datetime, HighSideCurrentRating text(20), LowSideCurrentRating text(20), CoolingType text(20), Earthing text(20), CompactType text(20), TertiaryVoltage integer, DTCType text(50), WeightofOil text(8), OilQuantity text(20), TransformerWeight text(20),
      PercentageLoading text(20), NeutralEarthing text(20), TemperatureRisingWDG text(20), TemperatureRisingOil text(20), Ownership text(20), LifeSpan text(20), SwitchID text(20), TapLocation text(50), DTUtilization text(9), HTConsumerNumber text(12), LoadTapChangerIndicator text(20), MagnetizingCurrent double, NumberofWays text(5), FacilityID text(20), Metering text(8), NoLoadLoss double, CopperLoss double, TotalLoad double, Material text(50), CurrentRating integer, RatedAmps text(50), SGEquipmentIDFK long, CODE text(14), SHAPE_STLength__ double, _OBJECTID text(200), X1 text(200), Y1 text(200), FromNodeId text(200), ToNodeId text(200), Phase text(200),
      fme_rejection_code text(200)

Bookmark: New Bookmark
CYMEBREAKINGSECTION
    VOLTAGE = @Value(Voltage)
    X = @Value(X)
    _ELEMENT_INDEX = @Value(_element_index)
    GISID = @Value(GISID)
    TG_COORDINATES = @Value(TG_Coordinates)
    Y = @Value(Y)
    Output_Overhead_TempSection_Breaked -> Junction_12
    Output_TempSection_Breaked -> CYMEBREAKINGSECTION_Output_TempSection_Breaked_-__TempSection_Breaked
    Output_TempSection_Breaked -> DEVICESECTION [BREAKEDSECTION]
    Output_BreakedTempNode -> Junction_6
CYMEBREAKINGSECTION_Output_TempSection_Breaked_-__TempSection_Breaked: Junction
    -> TempSection_Breaked (writer MDB_ADO_1)
    -> FinalSection (writer MDB_ADO_1)
TempSection_Breaked (writer MDB_ADO_1)
    attributes: SectionId text(200), FromNodeId text(200), FromNodeIndex text(200), ToNodeId text(200), ToNodeIndex text(200), Phase text(200), ZoneID text(200), SubNetworkId text(200), EnvironmentID text(200)
Junction_12
    -> Junction_13
Junction_6
    -> Junction_7

Bookmark: NODE
TempNode (writer MDB_ADO_1)
    attributes: NodeId text(200), X text(200), Y text(200), GISID text(200)

Bookmark: INTERMEDIATE NODES
TGNODE_INTERMEDIATENODES (writer MDB_ADO_1)
    attributes: SectionID text(50), SeqNumber text(200), CoordX text(50), CoordY text(50), IsBreakPoint text(50), BreakPointLocation text(50)

Bookmark: SUPPORT STRUCTURE
SUPPORTSTRUCTURE (reader SDE30_1) [off]
    attributes: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
FEEDERPILLAR (reader SDE30_1) [off]
    attributes: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

Bookmark: New Bookmark
JUMPER (reader SDE30_1) [off]
    attributes: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
CABLEJOINT (reader SDE30_1) [off]
    attributes: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

Bookmark: SUBSTATION ( POINT )
anc_Output: Junction [off]
SUBSTATION (reader SDE30_1) [off]
    attributes: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

FME custom transformer CYMELOAD

Parameters:
- BUILDINGID = @Value(BuildingID)   # BuildingID
- CABLESIZE = @Value(CableSize)   # CableSize
- CABLETYPE = @Value(CableType)   # CableType
- CIRCLE = @Value(Circle)   # Circle
- CONDUCTORMATERIAL = @Value(ConductorMaterial)   # ConductorMaterial
- CONNECTEDTOPOLE = @Value(ConnectedToPole)   # ConnectedToPole
- CONNECTIONSTATE = @Value(ConnectionState)   # ConnectionState
- CONSUMERCOUNT = @Value(ConsumerCount)   # ConsumerCount
- CONSUMERNUMBER = @Value(ConsumerNumber)   # ConsumerNumber
- CONSUMPTIONTYPE = @Value(ConsumptionType)   # ConsumptionType
- COST = @Value(Cost)   # Cost
- DIVISION = @Value(Division)   # Division
- ENABLED = @Value(Enabled)   # Enabled
- FEEDERCODE = @Value(FeederCode)   # FeederCode
- FEEDERID = @Value(FeederID)   # FeederID
- FEEDERINFO = @Value(FEEDERINFO)
- FEEDERNAME = @Value(FeederName)   # FeederName
- GISID = @Value(GISID)
- INSULATIONTYPE = @Value(InsulationType)   # InsulationType
- NAME = @Value(Name)   # Name
- NIN = @Value(NIN)
- NUMBEROFCIRCUITS = @Value(NumberOfCircuits)   # NumberOfCircuits
- NUMBEROFCORE = @Value(NumberOfCore)   # NumberOfCore
- OBJECTID = @Value(OBJECTID)
- PHASEDESIGNATION = @Value(Phasedesignation)   # Phasedesignation
- SANCTIONEDLOAD = @Value(SanctionedLoad)   # SanctionedLoad
- X = @Value(X)
- Y = @Value(Y)
- NODEID = @Value(NodeId)   # NodeId
- _ELEMENT_INDEX = @Value(_element_index)   # Element Index
- _OBJECTID = @Value(_OBJECTID)   # Objectid
- ADDITIONALCONDUCTOR = @Value(AdditionalConductor)   # AdditionalConductor
- ADOPTEDTAP = @Value(AdoptedTap)   # AdoptedTap
- ANCILLARYROLE = @Value(AncillaryRole)   # AncillaryRole
- ARMOURED = @Value(Armoured)   # Armoured
- AUXILIARYSUPPLY = @Value(AuxiliarySupply)   # AuxiliarySupply
- BREAKINGCURRENT = @Value(BreakingCurrent)   # BreakingCurrent
- CAPACITYINKVA = @Value(CapacityInKVA)   # CapacityInKVA
- CAPACITYINKVAR = @Value(CapacityInKVAR)   # CapacityInKVAR
- CLASS = @Value(Class)   # Class
- COMPACTTYPE = @Value(CompactType)   # CompactType
- CONDUCTORSIZE = @Value(ConductorSize)   # ConductorSize
- CONDUCTORTYPE = @Value(ConductorType)   # ConductorType
- CONFIGURATION = @Value(Configuration)   # Configuration
- COOLINGTYPE = @Value(CoolingType)   # CoolingType
- COPPERLOSS = @Value(CopperLoss)   # CopperLoss
- CREATED_DATE = @Value(created_date)   # Created Date
- CREATED_USER = @Value(created_user)   # Created User
- CSPTYPE = @Value(CSPType)   # CSPType
- CTPTCOMBINED = @Value(CTPTCombined)   # CTPTCombined
- CURRENTRATING = @Value(CurrentRating)   # CurrentRating
- CUSTOMERCLASSCODE = @Value(CustomerClassCode)   # CustomerClassCode
- DATEOFCOMMISSIONING = @Value(DateOfCommissioning)   # DateOfCommissioning
- DATEOFMANUFACTURING = @Value(DateOfManufacturing)   # DateOfManufacturing
- DTCCODE = @Value(DTCCode)   # DTCCode
- DTCCODEDETAILS = @Value(DTCCodeDetails)   # DTCCodeDetails
- DTCCONDITION = @Value(DTCCondition)   # DTCCondition
- DTCNAME = @Value(DTCName)   # DTCName
- DTCTYPE = @Value(DTCType)   # DTCType
- EAEQUIPMENT = @Value(EAEquipment)   # EAEquipment
- EARTHING = @Value(Earthing)   # Earthing
- EXSTING_CESU_DTC_CODE = @Value(Exsting_Cesu_DTC_Code)   # Exsting Cesu Dtc Code
- FACILITYID = @Value(FacilityID)   # FacilityID
- FAGEND = @Value(FagEnd)   # FagEnd
- FAULTCURRENT = @Value(FaultCurrent)   # FaultCurrent
- FEEDERID2 = @Value(FeederID2)   # FeederID2
- FROM_GISID = @Value(FROM_GISID)   # From Gisid
- HIGHSIDECURRENTRATING = @Value(HighSideCurrentRating)   # HighSideCurrentRating
- HIGHSIDEVOLTAGE = @Value(HighSideVoltage)   # HighSideVoltage
- HTPROTECTION = @Value(HTProtection)   # HTProtection
- IMPEDANCE = @Value(Impedance)   # Impedance
- INSTALLEDLOCATION = @Value(InstalledLocation)   # InstalledLocation
- JOBNUMBER = @Value(JobNumber)   # JobNumber
- LAST_EDITED_DATE = @Value(last_edited_date)   # Last Edited Date
- LAST_EDITED_USER = @Value(last_edited_user)   # Last Edited User
- LASTMAINTENANCEDATE = @Value(LastMaintenanceDate)   # LastMaintenanceDate
- LIFESPAN = @Value(LifeSpan)   # LifeSpan
- LOADTAPCHANGERINDICATOR = @Value(LoadTapChangerIndicator)   # LoadTapChangerIndicator
- LOCATIONCODE_X = @Value(LocationCode_X)   # Locationcode X
- LOCATIONCODE_Y = @Value(LocationCode_Y)   # Locationcode Y
- LOCATIONID = @Value(LocationID)   # LocationID
- LOWSIDECURRENTRATING = @Value(LowSideCurrentRating)   # LowSideCurrentRating
- LOWSIDEVOLTAGE = @Value(LowSideVoltage)   # LowSideVoltage
- LTPROTECTION = @Value(LTProtection)   # LTProtection
- MAGNETIZINGCURRENT = @Value(MagnetizingCurrent)   # MagnetizingCurrent
- MAKE = @Value(Make)   # Make
- MAKINGCAPACITY = @Value(MakingCapacity)   # MakingCapacity
- MANUFACTURINGYEAR = @Value(ManufacturingYear)   # ManufacturingYear
- MAPID = @Value(MapID)   # MapID
- MAT_OF_ADD_CONDUCTOR = @Value(Mat_Of_Add_Conductor)   # Mat Of Add Conductor
- MAT_OF_NEUTRAL_CONDUCTOR = @Value(Mat_Of_Neutral_Conductor)   # Mat Of Neutral Conductor
- MATERIAL = @Value(Material)   # Material
- MAXIMUMDEMAND = @Value(MaximumDemand)   # MaximumDemand
- MAXIMUMTAP = @Value(MaximumTap)   # MaximumTap
- MECHANISM = @Value(Mechanism)   # Mechanism
- MINIMUMTAP = @Value(MinimumTap)   # MinimumTap
- MMELECTRICTRACEWEIGHT = @Value(MMELECTRICTRACEWEIGHT)
- MULTIPLYINGFACTOR = @Value(MultiplyingFactor)   # MultiplyingFactor
- NEUTRALCONDUCTOR = @Value(NeutralConductor)   # NeutralConductor
- NEUTRALEARTHING = @Value(NeutralEarthing)   # NeutralEarthing
- NOLOADLOSS = @Value(NoLoadLoss)   # NoLoadLoss
- NORMALPOSITION_A = @Value(NormalPosition_A)   # Normalposition A
- NORMALPOSITION_B = @Value(NormalPosition_B)   # Normalposition B
- NORMALPOSITION_C = @Value(NormalPosition_C)   # Normalposition C
- NORMALRATEDCURRENT = @Value(NormalRatedCurrent)   # NormalRatedCurrent
- NORMALSTATUS = @Value(NormalStatus)   # NormalStatus
- NUMBEROFSTEPS = @Value(NumberOfSteps)   # NumberOfSteps
- NUMBEROFWAYS = @Value(NumberOfWays)   # NumberOfWays
- NUMBEROFWIRES = @Value(NumberOfWires)   # NumberOfWires
- OILQUANTITY = @Value(OilQuantity)   # OilQuantity
- OPERATINGSEQUENCE = @Value(OperatingSequence)   # OperatingSequence
- OVERHEADHEIGHT = @Value(OverheadHeight)   # OverheadHeight
- OWNERSHIP = @Value(Ownership)   # Ownership
- PERCENTAGEIMPEDANCE = @Value(PercentageImpedance)   # PercentageImpedance
- PERCENTAGELOADING = @Value(PercentageLoading)   # PercentageLoading
- PRESENTPOSITION_B = @Value(PresentPosition_B)   # Presentposition B
- PRESENTPOSITION_R = @Value(PresentPosition_R)   # Presentposition R
- PRESENTPOSITION_Y = @Value(PresentPosition_Y)   # Presentposition Y
- RATEDAMPS = @Value(RatedAmps)   # RatedAmps
- RATEDCURRENT = @Value(RatedCurrent)   # RatedCurrent
- RATEDPOWER = @Value(RatedPower)   # RatedPower
- RATING = @Value(Rating)   # Rating
- REACTIVEBREAKINGCURRENT = @Value(ReactiveBreakingCurrent)   # ReactiveBreakingCurrent
- RESISTANCE = @Value(Resistance)   # Resistance
- SAPID = @Value(SAPID)
- SECTION = @Value(Section)   # Section
- SERIALNUMBER = @Value(SerialNumber)   # SerialNumber
- SETTING = @Value(Setting)   # Setting
- SHAPE_STLENGTH__ = @Value(SHAPE_STLength__)   # Shape Stlength
- SHUNTREACTANCE = @Value(ShuntReactance)   # ShuntReactance
- SIZE_OF_ADD_CONDUCTOR = @Value(Size_Of_Add_Conductor)   # Size Of Add Conductor
- SIZE_OF_ADD_CONDUCTORS = @Value(Size_Of_Add_Conductors)   # Size Of Add Conductors
- SIZE_OF_NEUTRAL_CONDUCTOR = @Value(Size_Of_Neutral_Conductor)   # Size Of Neutral Conductor
- STARRATING = @Value(StarRating)   # StarRating
- SUBDIVISION = @Value(Subdivision)   # Subdivision
- SUBSTATIONCODE = @Value(SubstationCode)   # SubstationCode
- SUBSTATIONNAME = @Value(SubstationName)   # SubstationName
- SUBTYPE = @Value(SubType)   # SubType
- SURVEYORREMARK = @Value(SurveyorRemark)   # SurveyorRemark
- SWITCHID = @Value(SwitchID)   # SwitchID
- SYMMETRICALBREAKINGCURRENT = @Value(SymmetricalBreakingCurrent)   # SymmetricalBreakingCurrent
- TAPLOCATION = @Value(TapLocation)   # TapLocation
- TEMPERATURERISINGOIL = @Value(TemperatureRisingOil)   # TemperatureRisingOil
- TEMPERATURERISINGWDG = @Value(TemperatureRisingWDG)   # TemperatureRisingWDG
- TERTIARYVOLTAGE = @Value(TertiaryVoltage)   # TertiaryVoltage
- TG_COORDINATES = @Value(TG_Coordinates)   # Tg Coordinates
- TO_GISID = @Value(TO_GISID)   # To Gisid
- TOTALLOAD = @Value(TotalLoad)   # TotalLoad
- TOTALLOSS = @Value(TotalLoss)   # TotalLoss
- TRACINGSTATUS = @Value(TracingStatus)   # TracingStatus
- TRANSFORMERMOUNTING = @Value(TransformerMounting)   # TransformerMounting
- TRANSFORMERWEIGHT = @Value(TransformerWeight)   # TransformerWeight
- TYPE = @Value(Type)   # Type
- TYPEOFCORE = @Value(TypeOfCore)   # TypeOfCore
- TYPEOFSUPPORT = @Value(TypeOfSupport)   # TypeOfSupport
- VECTORGROUP = @Value(VectorGroup)   # VectorGroup
- VOLTAGE = @Value(Voltage)   # Voltage
- WARRANTY = @Value(Warranty)   # Warranty
- WEIGHTOFOILL = @Value(WeightOfOill)   # WeightOfOill
- WORKORDERID = @Value(WorkOrderID)   # WorkOrderID
- ZONE = @Value(Zone)   # Zone

PRISEC (input)
    -> AttributeRemover
NODES (input)
    -> AttributeRemover_2
SERVICEPOINT (input)
    -> AttributeCreator
AttributeCreator_5
    ATTR_TABLE = SET_TO DeviceNumber = @Value(TG_SERVICE_GISID)
    -> Output (output)
Output_2 (output)

Bookmark: New Bookmark
AttributeRemover
    REMOVE_ATTRS = CapacityInKVAR,ShuntReactance,ConsumerNumber,Size_Of_Add_Conductors,OverheadHeight,PresentPosition_B,_OBJECTID,FacilityID,InstalledLocation,NormalRatedCurrent,CurrentRating,MMELECTRICTRACEWEIGHT,CableType,FaultCurrent,last_edited_user,NIN,PercentageLoading,TertiaryVoltage,Type,TotalLoss,JobNumber,NumberOfCore,RatedCurrent,ConsumptionType,Ownership,CableSize,DateOfCommissioning,DTCType,LowSideVoltage,TypeOfSupport,DTCCode,TemperatureRisingOil,TemperatureRisingWDG,AuxiliarySupply,Mechanism,SubType,RatedAmps,Armoured,CompactType,created_user,ConductorSize,Warranty,NumberOfCircuits,AncillaryRole,LocationCode_X,MinimumTap,NeutralConductor,LowSideCurrentRating,Size_Of_Add_Conductor,FeederID2,ConsumerCount,AdditionalConductor,NormalPosition_A,SymmetricalBreakingCurrent,Configuration,LocationCode_Y,Name,TO_GISID,FagEnd,NumberOfWays,TapLocation,DTCCodeDetails,Earthing,MultiplyingFactor,PresentPosition_R,NeutralEarthing,NodeId,Impedance,TG_Coordinates,BuildingID,created_date,Mat_Of_Neutral_Conductor,InsulationType,SanctionedLoad,CSPType,LifeSpan,SurveyorRemark,WorkOrderID,Division,CoolingType,TracingStatus,TransformerMounting,NormalPosition_B,last_edited_date,SerialNumber,DateOfManufacturing,ConductorType,ConductorMaterial,NumberOfWires,MagnetizingCurrent,_element_index,HTProtection,FeederCode,FROM_GISID,Size_Of_Neutral_Conductor,LTProtection,HighSideVoltage,MaximumTap,HighSideCurrentRating,NoLoadLoss,PresentPosition_Y,TotalLoad,Make,OilQuantity,StarRating,Zone,CTPTCombined,CustomerClassCode,Circle,ManufacturingYear,ConnectionState,Enabled,Setting,SwitchID,Phasedesignation,FEEDERINFO,Cost,DTCName,NormalPosition_C,SAPID,SubstationCode,Material,Rating,CopperLoss,FeederName,Exsting_Cesu_DTC_Code,Mat_Of_Add_Conductor,Subdivision,ReactiveBreakingCurrent,AdoptedTap,NormalStatus,SHAPE_STLength__,TransformerWeight,EAEquipment,ConnectedToPole,Resistance,MakingCapacity,LocationID,MaximumDemand,LastMaintenanceDate,VectorGroup,DTCCondition,TypeOfCore,MapID,RatedPower,SubstationName,WeightOfOill,NumberOfSteps,Voltage,BreakingCurrent,OBJECTID,PercentageImpedance,OperatingSequence,CapacityInKVA,Class,LoadTapChangerIndicator,Section
    -> StringConcatenator
StringConcatenator
    PARM_LINE = @Value(X)_@Value(Y)
    VAL_ATTR = TG_XY
    ACTION = Create New Attribute
    -> AttributeCreator_4
AttributeCreator_4
    ATTR_TABLE = SET_TO SECTIONID = @Value(GISID)
    -> FeatureMerger_5 [REQUESTOR]
AttributeRemover_2
    REMOVE_ATTRS = CapacityInKVAR,ShuntReactance,ConsumerNumber,Size_Of_Add_Conductors,OverheadHeight,PresentPosition_B,_OBJECTID,FacilityID,InstalledLocation,NormalRatedCurrent,CurrentRating,MMELECTRICTRACEWEIGHT,CableType,FaultCurrent,last_edited_user,NIN,PercentageLoading,TertiaryVoltage,Type,TotalLoss,JobNumber,NumberOfCore,RatedCurrent,ConsumptionType,Ownership,CableSize,DateOfCommissioning,DTCType,LowSideVoltage,TypeOfSupport,DTCCode,TemperatureRisingOil,Y,TemperatureRisingWDG,AuxiliarySupply,Mechanism,SubType,RatedAmps,Armoured,CompactType,created_user,ConductorSize,Warranty,NumberOfCircuits,AncillaryRole,LocationCode_X,MinimumTap,NeutralConductor,LowSideCurrentRating,Size_Of_Add_Conductor,FeederID2,ConsumerCount,AdditionalConductor,NormalPosition_A,SymmetricalBreakingCurrent,Configuration,X,LocationCode_Y,Name,TO_GISID,FagEnd,NumberOfWays,TapLocation,DTCCodeDetails,Earthing,MultiplyingFactor,PresentPosition_R,NeutralEarthing,Impedance,TG_Coordinates,BuildingID,created_date,Mat_Of_Neutral_Conductor,InsulationType,SanctionedLoad,CSPType,LifeSpan,SurveyorRemark,WorkOrderID,Division,CoolingType,TracingStatus,TransformerMounting,NormalPosition_B,last_edited_date,SerialNumber,DateOfManufacturing,ConductorType,ConductorMaterial,NumberOfWires,MagnetizingCurrent,_element_index,HTProtection,FeederCode,FROM_GISID,Size_Of_Neutral_Conductor,LTProtection,HighSideVoltage,MaximumTap,HighSideCurrentRating,NoLoadLoss,PresentPosition_Y,TotalLoad,Make,OilQuantity,StarRating,Zone,CTPTCombined,CustomerClassCode,Circle,ManufacturingYear,ConnectionState,Enabled,Setting,SwitchID,Phasedesignation,FEEDERINFO,Cost,DTCName,NormalPosition_C,SAPID,SubstationCode,Material,Rating,CopperLoss,FeederName,Exsting_Cesu_DTC_Code,Mat_Of_Add_Conductor,Subdivision,ReactiveBreakingCurrent,AdoptedTap,NormalStatus,SHAPE_STLength__,TransformerWeight,EAEquipment,ConnectedToPole,Resistance,MakingCapacity,LocationID,MaximumDemand,LastMaintenanceDate,VectorGroup,DTCCondition,TypeOfCore,MapID,RatedPower,SubstationName,WeightOfOill,NumberOfSteps,Voltage,BreakingCurrent,OBJECTID,PercentageImpedance,OperatingSequence,CapacityInKVA,Class,LoadTapChangerIndicator,Section
    -> AttributeCreator_2
AttributeCreator_2
    ATTR_TABLE = SET_TO TG_NODES_GISID = @Value(GISID)
    -> FeatureMerger_4 [REQUESTOR]
AttributeCreator
    ATTR_TABLE = SET_TO TG_SERVICE_GISID = @Value(GISID)
    -> AttributeRemover_3
AttributeRemover_3
    REMOVE_ATTRS = CapacityInKVAR,ShuntReactance,ConsumerNumber,Size_Of_Add_Conductors,OverheadHeight,PresentPosition_B,_OBJECTID,FacilityID,InstalledLocation,NormalRatedCurrent,CurrentRating,MMELECTRICTRACEWEIGHT,CableType,FaultCurrent,last_edited_user,NIN,PercentageLoading,TertiaryVoltage,Type,TotalLoss,JobNumber,NumberOfCore,RatedCurrent,ConsumptionType,Ownership,CableSize,DateOfCommissioning,DTCType,LowSideVoltage,TypeOfSupport,DTCCode,TemperatureRisingOil,Y,TemperatureRisingWDG,AuxiliarySupply,Mechanism,SubType,RatedAmps,Armoured,CompactType,created_user,ConductorSize,Warranty,NumberOfCircuits,AncillaryRole,LocationCode_X,MinimumTap,NeutralConductor,LowSideCurrentRating,Size_Of_Add_Conductor,FeederID2,AdditionalConductor,NormalPosition_A,SymmetricalBreakingCurrent,Configuration,X,LocationCode_Y,Name,TO_GISID,FagEnd,NumberOfWays,TapLocation,DTCCodeDetails,Earthing,MultiplyingFactor,PresentPosition_R,NeutralEarthing,NodeId,Impedance,TG_Coordinates,created_date,Mat_Of_Neutral_Conductor,InsulationType,SanctionedLoad,CSPType,LifeSpan,SurveyorRemark,WorkOrderID,Division,CoolingType,TracingStatus,TransformerMounting,NormalPosition_B,last_edited_date,SerialNumber,DateOfManufacturing,ConductorType,TG_SERVICE_GISID,ConductorMaterial,NumberOfWires,MagnetizingCurrent,_element_index,HTProtection,FeederCode,FROM_GISID,Size_Of_Neutral_Conductor,LTProtection,HighSideVoltage,MaximumTap,HighSideCurrentRating,NoLoadLoss,PresentPosition_Y,TotalLoad,Make,OilQuantity,StarRating,Zone,CTPTCombined,CustomerClassCode,Circle,ManufacturingYear,ConnectionState,Setting,SwitchID,FEEDERINFO,Cost,DTCName,NormalPosition_C,SAPID,SubstationCode,Material,Rating,CopperLoss,FeederName,Exsting_Cesu_DTC_Code,Mat_Of_Add_Conductor,Subdivision,ReactiveBreakingCurrent,AdoptedTap,NormalStatus,SHAPE_STLength__,TransformerWeight,EAEquipment,Resistance,MakingCapacity,LocationID,MaximumDemand,LastMaintenanceDate,VectorGroup,DTCCondition,TypeOfCore,MapID,RatedPower,SubstationName,WeightOfOill,NumberOfSteps,BreakingCurrent,OBJECTID,PercentageImpedance,OperatingSequence,CapacityInKVA,Class,LoadTapChangerIndicator,Section
    -> AttributeCreator_3
AttributeCreator_3
    ATTR_TABLE = SET_TO TG_SERVICE_GISID = @Value(GISID)
    -> FeatureMerger_4 [SUPPLIER]
FeatureMerger_4
    ATTR_ACCUM_MODE = Merge Supplier
    PROCESS_DUPS = No
    MERGE_TYPE = Attributes Only
    SUPPLIERS_FIRST = No
    JOIN_KEYS = @Value(TG_NODES_GISID) @Value(TG_SERVICE_GISID) AUTO
    IGNORE_NULLS = No
    REJECT_NULL_MISSING_KEYS = No
    ATTR_CONFLICT_RES = Use Requestor
    MERGED -> FeatureMerger_5 [SUPPLIER]
    <REJECTED> -> Output_2 (output)
FeatureMerger_5
    ATTR_ACCUM_MODE = Merge Supplier
    PROCESS_DUPS = No
    MERGE_TYPE = Attributes Only
    SUPPLIERS_FIRST = No
    JOIN_KEYS = @Value(TG_XY) @Value(NodeId) AUTO
    IGNORE_NULLS = No
    REJECT_NULL_MISSING_KEYS = No
    ATTR_CONFLICT_RES = Use Requestor
    MERGED -> AttributeCreator_5
    <REJECTED> -> Output_3 (output)
Output_3 (output)
Output (output)

FME custom transformer DEVICESECTION

Parameters:
- NODEID = @Value(NodeId)   # NodeId
- TG_DTGISID = @Value(TG_DTGISID)   # Tg Dtgisid
- SECTIONID = @Value(SectionId)   # SectionId
- TONODEID = @Value(ToNodeId)   # ToNodeId
- SWITCHID = @Value(SwitchID)   # SwitchID
- TG_SWITCHGISID = @Value(TG_SWITCHGISID)   # Tg Switchgisid
- TG_FUSEGISID = @Value(TG_FUSEGISID)   # Tg Fusegisid
- FROMNODEID = @Value(FromNodeId)   # FromNodeId

BREAKER (input)
    -> FeatureMerger_4 [SUPPLIER]
DT (input)
    -> FeatureMerger_10 [SUPPLIER]
SWITCH (input)
    -> FeatureMerger_2 [SUPPLIER]
    -> FeatureMerger_7 [REQUESTOR]
FUSE (input)
    -> FeatureMerger_3 [SUPPLIER]
    -> FeatureMerger_8 [REQUESTOR]
BREAKEDSECTION (input)
    -> FeatureMerger_10 [REQUESTOR]
    -> FeatureMerger_2 [REQUESTOR]
    -> FeatureMerger_3 [REQUESTOR]
    -> FeatureMerger_4 [REQUESTOR]
    -> FeatureMerger_5 [REQUESTOR]
    -> FeatureMerger_6 [REQUESTOR]
FeatureMerger_4
    ATTR_ACCUM_MODE = Merge Supplier
    PROCESS_DUPS = No
    MERGE_TYPE = Attributes Only
    SUPPLIERS_FIRST = No
    JOIN_KEYS = @Value(FromNodeId) @Value(NodeId) AUTO
    IGNORE_NULLS = No
    REJECT_NULL_MISSING_KEYS = No
    ATTR_CONFLICT_RES = Use Requestor
    MERGED -> BREAKER (output)
    UNUSED_SUPPLIER -> FeatureMerger_5 [SUPPLIER]
FeatureMerger_5
    ATTR_ACCUM_MODE = Merge Supplier
    PROCESS_DUPS = No
    MERGE_TYPE = Attributes Only
    SUPPLIERS_FIRST = No
    JOIN_KEYS = @Value(ToNodeId) @Value(NodeId) AUTO
    IGNORE_NULLS = No
    REJECT_NULL_MISSING_KEYS = No
    ATTR_CONFLICT_RES = Use Requestor
    MERGED -> BREAKER (output)
BREAKER (output)
FeatureMerger_10
    ATTR_ACCUM_MODE = Merge Supplier
    PROCESS_DUPS = No
    MERGE_TYPE = Attributes Only
    SUPPLIERS_FIRST = No
    JOIN_KEYS = @Value(ToNodeId) @Value(NodeId) AUTO
    IGNORE_NULLS = No
    REJECT_NULL_MISSING_KEYS = No
    ATTR_CONFLICT_RES = Use Requestor
    MERGED -> DT (output)
    UNUSED_SUPPLIER -> FeatureMerger_6 [SUPPLIER]
FeatureMerger_6
    ATTR_ACCUM_MODE = Merge Supplier
    PROCESS_DUPS = No
    MERGE_TYPE = Attributes Only
    SUPPLIERS_FIRST = No
    JOIN_KEYS = @Value(FromNodeId) @Value(NodeId) AUTO
    IGNORE_NULLS = No
    REJECT_NULL_MISSING_KEYS = No
    ATTR_CONFLICT_RES = Use Requestor
    MERGED -> DT (output)
DT (output)
FeatureMerger_2
    ATTR_ACCUM_MODE = Merge Supplier
    PROCESS_DUPS = No
    MERGE_TYPE = Attributes Only
    SUPPLIERS_FIRST = No
    JOIN_KEYS = @Value(ToNodeId) @Value(NodeId) AUTO
    IGNORE_NULLS = No
    REJECT_NULL_MISSING_KEYS = No
    ATTR_CONFLICT_RES = Use Requestor
    MERGED -> SWITCH (output)
    UNUSED_SUPPLIER -> FeatureMerger_7 [SUPPLIER]
FeatureMerger_7
    ATTR_ACCUM_MODE = Merge Supplier
    PROCESS_DUPS = No
    MERGE_TYPE = Attributes Only
    SUPPLIERS_FIRST = No
    JOIN_KEYS = @Value(FromNodeId) @Value(NodeId) AUTO
    IGNORE_NULLS = No
    REJECT_NULL_MISSING_KEYS = No
    ATTR_CONFLICT_RES = Use Requestor
    MERGED -> SWITCH (output)
SWITCH (output)
FeatureMerger_3
    ATTR_ACCUM_MODE = Merge Supplier
    PROCESS_DUPS = No
    MERGE_TYPE = Attributes Only
    SUPPLIERS_FIRST = No
    JOIN_KEYS = @Value(FromNodeId) @Value(NodeId) AUTO
    IGNORE_NULLS = No
    REJECT_NULL_MISSING_KEYS = No
    ATTR_CONFLICT_RES = Use Requestor
    MERGED -> FUSE (output)
    UNUSED_SUPPLIER -> FeatureMerger_8 [SUPPLIER]
FeatureMerger_8
    ATTR_ACCUM_MODE = Merge Supplier
    PROCESS_DUPS = No
    MERGE_TYPE = Attributes Only
    SUPPLIERS_FIRST = No
    JOIN_KEYS = @Value(ToNodeId) @Value(NodeId) AUTO
    IGNORE_NULLS = No
    REJECT_NULL_MISSING_KEYS = No
    ATTR_CONFLICT_RES = Use Requestor
    MERGED -> FUSE (output)
FUSE (output)

FME custom transformer CYMEBREAKINGSECTION

Parameters:
- _ELEMENT_INDEX = @Value(_element_index)   # Element Index
- GISID = @Value(GISID)
- TG_COORDINATES = @Value(TG_Coordinates)   # Tg Coordinates
- X = @Value(X)
- Y = @Value(Y)
- VOLTAGE = @Value(Voltage)   # Voltage

Input (input)
    -> Tester
Tester
    BOOL_OP = OR
    TEST_MODE = Automatic
    TEST_DESCRIPTION = ""
    TEST_CLAUSE = TEST @Value(GISID) CONTAINS BS
    PASSED -> StringConcatenator_2
StringConcatenator_2
    PARM_LINE = @Value(X)_@Value(Y)
    VAL_ATTR = TG_XY
    ACTION = Create New Attribute
    -> AttributeCreator_2
    -> AttributeCreator
AttributeCreator
    ATTR_TABLE = SET_TO ID = @sum(@Value(_element_index),1)
    -> StringConcatenator
StringConcatenator
    PARM_LINE = @Value(GISID)-@Value(ID)
    VAL_ATTR = SectionId
    ACTION = Create New Attribute
    -> AttributeCreator_5
AttributeCreator_5
    ATTR_TABLE = SET_TO FromNodeId = @Value(TG_XY)
    -> FeatureMerger_3 [REQUESTOR]
AttributeCreator_2
    ATTR_TABLE = SET_TO Index = @Value(_element_index)
    -> AttributeCreator_4
AttributeCreator_4
    ATTR_TABLE = SET_TO ToNodeId = @Value(TG_XY)
    -> FeatureMerger_3 [SUPPLIER]
FeatureMerger_3
    ATTR_ACCUM_MODE = Merge Supplier
    PROCESS_DUPS = No
    MERGE_TYPE = Attributes Only
    GROUP_BY = GISID
    SUPPLIERS_FIRST = No
    JOIN_KEYS = @Value(ID) @Value(Index) AUTO
    IGNORE_NULLS = No
    REJECT_NULL_MISSING_KEYS = No
    ATTR_CONFLICT_RES = Use Requestor
    MERGED -> Output_TempSection_Breaked (output)
    MERGED -> StringConcatenator_4
    MERGED -> AVM_BUSBAR
    <REJECTED> -> Output_TempIntermediate_Node (output)
AVM_BUSBAR: AttributeValueMapper
    DEFAULT_VALUE = KV
    VAL_ATTR = LineCableID
    LUT = 340,11KV_BUSBAR,210,0.43KV_BUSBAR,160,0.24KV_BUSBAR
    SRC = Voltage
    DIRECTION = Forward (Source To Destination)
    -> AttributeCreator_6
AttributeCreator_6
    ATTR_TABLE = SET_TO DeviceNumber = @Value(SectionId)
    -> AttributeCreator_7
AttributeCreator_7
    ATTR_TABLE:
      SET_TO DeviceNumber = @Value(SectionId)
      SET_TO SectionID = @Value(SectionId)
    -> LengthCalculator_3
LengthCalculator_3
    MULT = 1
    LEN_ATTR = Length
    DIM = 2
    -> AttributeCreator_3
    <REJECTED> -> Output_TempIntermediate_Node_2 (output)
AttributeCreator_3
    ATTR_TABLE = SET_TO ConnectionStatus = 0
    -> Output_Overhead_TempSection_Breaked (output)
Output_Overhead_TempSection_Breaked (output)
Output_TempIntermediate_Node_2 (output)
Output_TempSection_Breaked (output)
Output_TempIntermediate_Node (output)
StringConcatenator_4
    PARM_LINE = @Value(X)_@Value(Y)
    VAL_ATTR = NodeId
    ACTION = Create New Attribute
    -> Output_BreakedTempNode (output)
Output_BreakedTempNode (output)

FME custom transformer CYMESECTION

Parameters:
- CIRCLE = @Value(Circle)   # Circle
- DIVISION = @Value(Division)   # Division
- FEEDERID = @Value(FeederID)   # FeederID
- GISID = @Value(GISID)
- OBJECTID = @Value(OBJECTID)
- PHASEDESIGNATION = @Value(Phasedesignation)   # Phasedesignation
- SHAPE_STLENGTH__ = @Value(SHAPE_STLength__)   # Shape Stlength

Input (input)
    -> AttributeRemover_2
    -> Junction
    -> Junction_3
    -> Junction_5
    -> Junction_7
Note: Tester_8 : Input
Junction_3
    -> Junction_4
Note: Input
Junction_4
    -> Tester_8
Tester_8
    BOOL_OP = OR
    TEST_MODE = Automatic
    TEST_DESCRIPTION = ""
    TEST_CLAUSE = TEST @Value(GISID) CONTAINS SW
    PASSED -> AttributeCreator_8
AttributeCreator_8
    ATTR_TABLE = SET_TO TG_SWITCHGISID = @Value(GISID)
    -> FeatureMerger_8 [SUPPLIER]
Note: Tester_6 : Input
Junction
    -> Junction_2
Note: Input
Junction_2
    -> Tester_6
Note: Tester_12 : Input
Junction_5
    -> Junction_6
Note: Input
Junction_6
    -> Tester_12
Tester_12
    BOOL_OP = OR
    TEST_MODE = Automatic
    TEST_DESCRIPTION = ""
    TEST_CLAUSE = TEST @Value(GISID) CONTAINS FU
    PASSED -> AttributeCreator_10
AttributeCreator_10
    ATTR_TABLE = SET_TO TG_FUSEGISID = @Value(GISID)
    -> FeatureMerger_10 [SUPPLIER]
AttributeRemover
    REMOVE_ATTRS = _z,SHAPE_STLength__,Circle,OBJECTID,_x,Division,X,_node_number,Phasedesignation,Y,_y,FeederID
    -> Tester_5
    -> AttributeRemover_OUTPUT_-__Tester_4
AttributeRemover_OUTPUT_-__Tester_4: Junction
    -> Tester_4
    -> AttributeRemover_OUTPUT_-__Tester_4_Output_-__Tester_11
AttributeRemover_OUTPUT_-__Tester_4_Output_-__Tester_11: Junction
    -> Tester_11
    -> Tester_15
Tester_15
    BOOL_OP = OR
    TEST_MODE = Automatic
    TEST_DESCRIPTION = ""
    TEST_CLAUSE:
      TEST @Value(GISID) CONTAINS BS
      TEST @Value(GISID) CONTAINS SG
    PASSED -> Tester_17
Tester_17
    BOOL_OP = OR
    TEST_MODE = Automatic
    TEST_DESCRIPTION = ""
    TEST_CLAUSE:
      TEST @Value(GISID) CONTAINS BS
      TEST @Value(GISID) CONTAINS SG
    PASSED -> FeatureMerger_12 [REQUESTOR]
    PASSED -> FeatureMerger_13 [REQUESTOR]
Tester_11
    BOOL_OP = OR
    TEST_MODE = Automatic
    TEST_DESCRIPTION = ""
    TEST_CLAUSE:
      TEST @Value(GISID) CONTAINS BS
      TEST @Value(GISID) CONTAINS FU
    PASSED -> Tester_13
Tester_13
    BOOL_OP = OR
    TEST_MODE = Automatic
    TEST_DESCRIPTION = ""
    TEST_CLAUSE:
      TEST @Value(GISID) CONTAINS BS
      TEST @Value(GISID) CONTAINS FU
    PASSED -> FeatureMerger_10 [REQUESTOR]
    PASSED -> FeatureMerger_11 [REQUESTOR]
FeatureMerger_10
    ATTR_ACCUM_MODE = Merge Supplier
    PROCESS_DUPS = No
    MERGE_TYPE = Attributes Only
    GROUP_BY = GISID
    SUPPLIERS_FIRST = No
    JOIN_KEYS = @Value(GISID) @Value(TG_FUSEGISID) AUTO
    IGNORE_NULLS = No
    REJECT_NULL_MISSING_KEYS = No
    ATTR_CONFLICT_RES = Use Requestor
    MERGED -> FeatureMerger_11 [SUPPLIER]
    <REJECTED> -> Error
FeatureMerger_11
    ATTR_ACCUM_MODE = Merge Supplier
    PROCESS_DUPS = No
    MERGE_TYPE = Attributes Only
    SUPPLIERS_FIRST = No
    JOIN_KEYS = @Value(NodeId) @Value(NodeId) AUTO
    IGNORE_NULLS = No
    REJECT_NULL_MISSING_KEYS = No
    ATTR_CONFLICT_RES = Use Requestor
    MERGED -> Tester_14
    <REJECTED> -> Error
Tester_14
    BOOL_OP = OR
    TEST_MODE = Automatic
    TEST_DESCRIPTION = ""
    TEST_CLAUSE = TEST @Value(GISID) CONTAINS BS
    PASSED -> DuplicateFilter
DuplicateFilter
    INPUT_ORDERED_CHOICE = No
    KEYATTR = TG_FUSEGISID
    UNIQUE -> AttributeCreator_11
AttributeCreator_11
    ATTR_TABLE = SET_TO TG_BUSBARGISID = @Value(GISID)
    -> Output_FUSESECTION (output)
Output_FUSESECTION (output)
Error: AttributeCreator
    ATTR_TABLE = SET_TO TG_FUSEGISID = @Value(GISID)
Tester_4
    BOOL_OP = OR
    TEST_MODE = Automatic
    TEST_DESCRIPTION = ""
    TEST_CLAUSE:
      TEST @Value(GISID) CONTAINS BS
      TEST @Value(GISID) CONTAINS SW
    PASSED -> Tester_9
Tester_9
    BOOL_OP = OR
    TEST_MODE = Automatic
    TEST_DESCRIPTION = ""
    TEST_CLAUSE:
      TEST @Value(GISID) CONTAINS BS
      TEST @Value(GISID) CONTAINS SW
    PASSED -> FeatureMerger_8 [REQUESTOR]
    PASSED -> FeatureMerger_9 [REQUESTOR]
FeatureMerger_8
    ATTR_ACCUM_MODE = Merge Supplier
    PROCESS_DUPS = No
    MERGE_TYPE = Attributes Only
    GROUP_BY = GISID
    SUPPLIERS_FIRST = No
    JOIN_KEYS = @Value(GISID) @Value(TG_SWITCHGISID) AUTO
    IGNORE_NULLS = No
    REJECT_NULL_MISSING_KEYS = No
    ATTR_CONFLICT_RES = Use Requestor
    MERGED -> FeatureMerger_9 [SUPPLIER]
FeatureMerger_9
    ATTR_ACCUM_MODE = Merge Supplier
    PROCESS_DUPS = No
    MERGE_TYPE = Attributes Only
    SUPPLIERS_FIRST = No
    JOIN_KEYS = @Value(NodeId) @Value(NodeId) AUTO
    IGNORE_NULLS = No
    REJECT_NULL_MISSING_KEYS = No
    ATTR_CONFLICT_RES = Use Requestor
    MERGED -> Tester_10
Tester_10
    BOOL_OP = OR
    TEST_MODE = Automatic
    TEST_DESCRIPTION = ""
    TEST_CLAUSE = TEST @Value(GISID) CONTAINS BS
    PASSED -> DuplicateFilter_2
DuplicateFilter_2
    INPUT_ORDERED_CHOICE = No
    KEYATTR = TG_SWITCHGISID
    UNIQUE -> AttributeCreator_9
AttributeCreator_9
    ATTR_TABLE = SET_TO TG_BUSBARGISID = @Value(GISID)
    -> Output_SWITCHSECTION (output)
Output_SWITCHSECTION (output)
Output_DTSECTION (output)
Output_node (output)
Output_Section (output)
Output_TempNode (output)
Output_TempIntermediate_Node (output)
Output_TempIntermediate_Node_2 (output)
AVM_HTCABLE_P: AttributeValueMapper
    DEFAULT_VALUE = 0
    VAL_ATTR = TG_PHASE
    LUT = 1,A,2,B,3,C,4,AB,5,AC,6,BC,7,ABC
    SRC = Phasedesignation
    DIRECTION = Forward (Source To Destination)
    -> AttributeCreator_6
AttributeCreator_6
    ATTR_TABLE = SET_TO Length = @Value(SHAPE_STLength__)
    -> Output_TGLINE (output)
Output_TGLINE (output)
Note: Tester_16 : Input
Junction_7
    -> Junction_8
Note: Input
Junction_8
    -> Tester_16
Tester_16
    BOOL_OP = OR
    TEST_MODE = Automatic
    TEST_DESCRIPTION = ""
    TEST_CLAUSE = TEST @Value(GISID) CONTAINS SG
    PASSED -> AttributeCreator_13
AttributeCreator_13
    ATTR_TABLE = SET_TO TG_BREAKERGISID = @Value(GISID)
    -> FeatureMerger_12 [SUPPLIER]
FeatureMerger_12
    ATTR_ACCUM_MODE = Merge Supplier
    PROCESS_DUPS = No
    MERGE_TYPE = Attributes Only
    GROUP_BY = GISID
    SUPPLIERS_FIRST = No
    JOIN_KEYS = @Value(GISID) @Value(TG_BREAKERGISID) AUTO
    IGNORE_NULLS = No
    REJECT_NULL_MISSING_KEYS = No
    ATTR_CONFLICT_RES = Use Requestor
    MERGED -> FeatureMerger_13 [SUPPLIER]
    <REJECTED> -> Output_TempIntermediate_Node_6 (output)
FeatureMerger_13
    ATTR_ACCUM_MODE = Merge Supplier
    PROCESS_DUPS = No
    MERGE_TYPE = Attributes Only
    SUPPLIERS_FIRST = No
    JOIN_KEYS = @Value(NodeId) @Value(NodeId) AUTO
    IGNORE_NULLS = No
    REJECT_NULL_MISSING_KEYS = No
    ATTR_CONFLICT_RES = Use Requestor
    MERGED -> Tester_18
    <REJECTED> -> Output_TempIntermediate_Node_5 (output)
Tester_18
    BOOL_OP = OR
    TEST_MODE = Automatic
    TEST_DESCRIPTION = ""
    TEST_CLAUSE = TEST @Value(GISID) CONTAINS BS
    PASSED -> DuplicateFilter_4
DuplicateFilter_4
    INPUT_ORDERED_CHOICE = No
    KEYATTR = TG_BREAKERGISID
    UNIQUE -> AttributeCreator_14
AttributeCreator_14
    ATTR_TABLE = SET_TO TG_BUSBARGISID = @Value(GISID)
    -> Output_BREAKERSECTION (output)
Output_BREAKERSECTION (output)
Output_TempIntermediate_Node_5 (output)
Output_TempIntermediate_Node_6 (output)

Bookmark: DT SECTION
Tester_6
    BOOL_OP = OR
    TEST_MODE = Automatic
    TEST_DESCRIPTION = ""
    TEST_CLAUSE = TEST @Value(GISID) CONTAINS DT
    PASSED -> AttributeCreator_3
AttributeCreator_3
    ATTR_TABLE = SET_TO TG_DTGISID = @Value(GISID)
    -> FeatureMerger_6 [SUPPLIER]
Tester_5
    BOOL_OP = OR
    TEST_MODE = Automatic
    TEST_DESCRIPTION = ""
    TEST_CLAUSE:
      TEST @Value(GISID) CONTAINS BS
      TEST @Value(GISID) CONTAINS DT
    PASSED -> FeatureMerger_6 [REQUESTOR]
    PASSED -> FeatureMerger_7 [REQUESTOR]
FeatureMerger_6
    ATTR_ACCUM_MODE = Merge Supplier
    PROCESS_DUPS = No
    MERGE_TYPE = Attributes Only
    GROUP_BY = GISID
    SUPPLIERS_FIRST = No
    JOIN_KEYS = @Value(GISID) @Value(TG_DTGISID) AUTO
    IGNORE_NULLS = No
    REJECT_NULL_MISSING_KEYS = No
    ATTR_CONFLICT_RES = Use Requestor
    MERGED -> FeatureMerger_7 [SUPPLIER]
    <REJECTED> -> Output_TempIntermediate_Node_3 (output)
FeatureMerger_7
    ATTR_ACCUM_MODE = Merge Supplier
    PROCESS_DUPS = No
    MERGE_TYPE = Attributes Only
    SUPPLIERS_FIRST = No
    JOIN_KEYS = @Value(NodeId) @Value(NodeId) AUTO
    IGNORE_NULLS = No
    REJECT_NULL_MISSING_KEYS = No
    ATTR_CONFLICT_RES = Use Requestor
    MERGED -> Tester_7
    <REJECTED> -> Output_TempIntermediate_Node_4 (output)
Tester_7
    BOOL_OP = OR
    TEST_MODE = Automatic
    TEST_DESCRIPTION = ""
    TEST_CLAUSE = TEST @Value(GISID) CONTAINS BS
    PASSED -> DuplicateFilter_3
DuplicateFilter_3
    INPUT_ORDERED_CHOICE = No
    KEYATTR = TG_DTGISID
    UNIQUE -> AttributeCreator_7
AttributeCreator_7
    ATTR_TABLE = SET_TO TG_BUSBARGISID = @Value(GISID)
    -> Output_DTSECTION (output)
Output_TempIntermediate_Node_4 (output)
Output_TempIntermediate_Node_3 (output)

Bookmark: New Bookmark
AttributeRemover_2
    -> TopologyBuilder
    -> AVM_HTCABLE_P
TopologyBuilder
    PROP_ATTRS = No
    ALL_EDGES = Yes
    CLEAN_DATA = No
    GROUP_BY = GISID
    MAX = 0
    ALLOW_CYCLES = Yes
    OVERLAPPING_MODE = Yes
    NODE -> Lines_Coordinates_2
    LINE -> Lines_Coordinates
Lines_Coordinates: CoordinateConcatenator
    ELEMENT_DELIM = ,
    COORD_ATTR = _coordinates
    COORD_DELIM = |
    -> AttributeSplitter
AttributeSplitter
    TRIM_OPTION = Both
    ATTR_NAME = _coordinates
    DELIMITER = |
    DROP_EMPTY_PARTS = No
    LIST_NAME = sp
    -> ListExploder
ListExploder
    MODE = List Elements and Original Attributes
    LIST_ATTR = sp{}
    INDEX_ATTR = _element_index
    -> AttributeSplitter_2
AttributeSplitter_2
    TRIM_OPTION = Both
    ATTR_NAME = sp
    DELIMITER = ,
    DROP_EMPTY_PARTS = No
    LIST_NAME = XP
    -> AttributeCreator_2
AttributeCreator_2
    ATTR_TABLE:
      SET_TO X = @Value(XP{0})
      SET_TO Y = @Value(XP{1})
    -> AttributeRounder_2
AttributeRounder_2
    PLACES = 2
    ROUND_TYPE = Nearest
    SRC_ATTRS = X Y
    -> StringConcatenator_3
    -> FeatureMerger_3 [SUPPLIER]
    -> FeatureMerger_2 [SUPPLIER]
    -> StatisticsCalculator
    -> StringConcatenator_4
StringConcatenator_3
    PARM_LINE = @Value(X),@Value(Y)
    VAL_ATTR = TG_Coordinates
    ACTION = Create New Attribute
    -> FeatureMerger_5 [SUPPLIER]
    -> Output_Prisec (output)
Output_Prisec (output)

Bookmark: New Bookmark
Lines_Coordinates_2: CoordinateConcatenator
    ELEMENT_DELIM = ,
    COORD_ATTR = _coordinates
    COORD_DELIM = |
    -> AttributeSplitter_3
AttributeSplitter_3
    TRIM_OPTION = Both
    ATTR_NAME = _coordinates
    DELIMITER = |
    DROP_EMPTY_PARTS = No
    LIST_NAME = sp
    -> ListExploder_2
ListExploder_2
    MODE = List Elements and Original Attributes
    LIST_ATTR = sp{}
    INDEX_ATTR = _element_index
    -> AttributeSplitter_4
AttributeSplitter_4
    TRIM_OPTION = Both
    ATTR_NAME = sp
    DELIMITER = ,
    DROP_EMPTY_PARTS = No
    LIST_NAME = XP
    -> AttributeCreator_15
AttributeCreator_15
    ATTR_TABLE:
      SET_TO X = @Value(XP{0})
      SET_TO Y = @Value(XP{1})
    -> AttributeRounder_4
AttributeRounder_4
    PLACES = 2
    ROUND_TYPE = Nearest
    SRC_ATTRS = X Y
    -> StringConcatenator_4
StringConcatenator_4
    PARM_LINE = @Value(X)_@Value(Y)
    VAL_ATTR = NodeId
    ACTION = Create New Attribute
    -> AttributeRemover
    -> Output_node (output)

Bookmark: New Bookmark
StatisticsCalculator
    MIN_ATTR = _min
    PREPEND_ATTR_NAME_CHOICE = For multiple results only
    COMPUTE_HISTOGRAM = NO
    GROUP_BY = GISID
    STATS_ATTRS = _element_index
    MEDIAN_ATTR = _median
    MAX_ATTR = _max
    SUMMARY -> FeatureMerger_3 [REQUESTOR]
    SUMMARY -> FeatureMerger_2 [REQUESTOR]
    SUMMARY -> FeatureMerger_5 [REQUESTOR]
FeatureMerger_3
    ATTR_ACCUM_MODE = Merge Supplier
    PROCESS_DUPS = No
    MERGE_TYPE = Attributes Only
    GROUP_BY = GISID
    SUPPLIERS_FIRST = No
    JOIN_KEYS = @Value(_min) @Value(_element_index) AUTO
    IGNORE_NULLS = No
    REJECT_NULL_MISSING_KEYS = No
    ATTR_CONFLICT_RES = Use Requestor
    MERGED -> FeatureMerger_4 [REQUESTOR]
    <REJECTED> -> Aggregator_2
FeatureMerger_2
    ATTR_ACCUM_MODE = Merge Supplier
    PROCESS_DUPS = No
    MERGE_TYPE = Attributes Only
    GROUP_BY = GISID
    SUPPLIERS_FIRST = No
    JOIN_KEYS = @Value(_max) @Value(_element_index) AUTO
    IGNORE_NULLS = No
    REJECT_NULL_MISSING_KEYS = No
    ATTR_CONFLICT_RES = Use Requestor
    MERGED -> AttributeCreator
    <REJECTED> -> Error (output)
AttributeCreator
    ATTR_TABLE:
      SET_TO X1 = @Value(X)
      SET_TO Y1 = @Value(Y)
    -> FeatureMerger_4 [SUPPLIER]
FeatureMerger_4
    ATTR_ACCUM_MODE = Merge Supplier
    PROCESS_DUPS = No
    MERGE_TYPE = Attributes Only
    GROUP_BY = GISID
    SUPPLIERS_FIRST = No
    JOIN_KEYS = @Value(GISID) @Value(GISID) AUTO
    IGNORE_NULLS = No
    REJECT_NULL_MISSING_KEYS = No
    ATTR_CONFLICT_RES = Use Requestor
    MERGED -> StringConcatenator_2
    <REJECTED> -> Aggregator_2
Aggregator_2
    SEP = ,
    AGGREGATE_TYPE = Homogeneous Collection (If Possible)
    ID_SELECTION = ID and Parent ID
    ATTR_TO_TRAIT = Yes
    ACCUM_ATTRS_NAME = Use Attributes From One Feature
    MODE = Geometry - Assemble One Level
    PRESERVE_ID = No
    ORDERED = No
StringConcatenator_2
    PARM_LINE = @Value(X)_@Value(Y)
    VAL_ATTR = FromNodeId
    ACTION = Create New Attribute
    -> StringConcatenator
StringConcatenator
    PARM_LINE = @Value(X1)_@Value(Y1)
    VAL_ATTR = ToNodeId
    ACTION = Create New Attribute
    -> Tester
Tester
    BOOL_OP = OR
    TEST_MODE = Automatic
    TEST_DESCRIPTION = ""
    TEST_CLAUSE = TEST @Value(GISID) CONTAINS BS
    FAILED -> AVM_HTCABLE_P_2
AVM_HTCABLE_P_2: AttributeValueMapper
    DEFAULT_VALUE = 0
    VAL_ATTR = Phase
    LUT = 1,A,2,B,3,C,4,AB,5,AC,6,BC,7,ABC
    SRC = Phasedesignation
    DIRECTION = Forward (Source To Destination)
    -> AttributeCreator_12
AttributeCreator_12
    ATTR_TABLE = SET_TO SectionId = @Value(GISID)
    -> Output_Section (output)
    -> Output_TempNode (output)
Error (output)

Bookmark: New Bookmark
FeatureMerger_5
    ATTR_ACCUM_MODE = Merge Supplier
    PROCESS_DUPS = No
    MERGE_TYPE = Attributes Only
    GROUP_BY = GISID
    SUPPLIERS_FIRST = No
    JOIN_KEYS = @Value(_max) @Value(_element_index) AUTO
    IGNORE_NULLS = No
    REJECT_NULL_MISSING_KEYS = No
    ATTR_CONFLICT_RES = Use Requestor
    UNUSED_SUPPLIER -> Tester_2
    <REJECTED> -> Output_TempIntermediate_Node_2 (output)
Tester_2
    BOOL_OP = OR
    TEST_MODE = Automatic
    TEST_DESCRIPTION = ""
    TEST_CLAUSE = TEST @Value(GISID) CONTAINS BS
    FAILED -> Tester_3
Tester_3
    BOOL_OP = OR
    TEST_MODE = Automatic
    TEST_DESCRIPTION = ""
    TEST_CLAUSE = TEST @Value(_element_index) CONTAINS 0
    FAILED -> AttributeCreator_5
AttributeCreator_5
    ATTR_TABLE:
      SET_TO SectionID = @Value(GISID)
      SET_TO SeqNumber = @sub(@Value(_element_index),1)
      SET_TO CoordX = @Value(X)
      SET_TO CoordY = @Value(Y)
    -> Output_TempIntermediate_Node (output)

FME custom transformer CYMESOURCE

Parameters:
- FEEDERID = @Value(FeederId)   # FeederId
- FEEDERID2 = @Value(FeederId2)   # FeederId2
- FEEDERINFO = @Value(FeederInfo)   # FeederInfo
- FEEDERNAME = @Value(FeederName)   # FeederName
- FEEDERSOURCEINFO = @Value(FeederSourceInfo)   # FeederSourceInfo
- OBJECTID = @Value(OBJECTID)
- SUBSTATIONID = @Value(SubstationId)   # SubstationId
- SWITCHGEAROBJID = @Value(SwitchGearObjid)   # SwitchGearObjid
- TOSUBSTATIONID = @Value(ToSubStationID)   # ToSubStationID
- WORKORDERID = @Value(WorkOrderID)   # WorkOrderID

Bookmark: SOURCE
INPUT_CIRCUITSOURCE (input)
    -> AttributeRemover_11
AttributeRemover_11
    REMOVE_ATTRS = OBJECTID,FeederInfo,FeederId2,FeederSourceInfo,ToSubStationID,WorkOrderID
    -> Output (output)
Output (output)

FME custom transformer CYMETRANSFORMER

Input (input)
Output (output)
