FME workspace FeederList.fmw

Parameters:
- SourceDataset_SDE30 = GISDBDC   # Source Esri ArcSDE Dataset
- DestDataset_CSV2 = E:\Development\GIS-CYME Integration\Odisha ADCC RAPDRP\FME   # Destination CSV (Comma Separated Value) Folder
- Password = ttpl@987   # SQL
- DestDataset_MSSQL_ADO = CYME_TechGration_TPCODL   # Database
- Password_2 = ttpl@987   # SQL

Readers:
- SDE30_1: SDE30 from $(SourceDataset_SDE30)
- GEODATABASE_SDE_1: GEODATABASE_SDE

Writers:
- MSSQL_ADO_1: MSSQL_ADO to $(DestDataset_MSSQL_ADO)
- CSV2_1: CSV2 to $(DestDataset_CSV2)

Note: FeederList ArcGIS CYME FME Workbench file / Tech-Gration for ADCC@CESU , TPCODL / Version 9.0 / MSSQL ArcSDE / Author: Rajib Kumar / Created: Augest 01th, 2017 / Last Modified: June 05, 2019 / Last Modified: OCT 07, 2022 / This script creates the list of feeders that can be selected by the user / Trident Techlabs Pvt Ltd
SwitchGear (reader GEODATABASE_SDE_1)
    attributes: OBJECTID integer, InstalledLocation coded_domain("SWG Installed Location":smallint:1:Substation:2:DT:3:"Feeder Pillar":4:RMU:5:"HT Consumer":6:Pole), InstalledLocation_resolved char(254), LocationID char(50), GISID char(50), NIN char(50), SubType smallint, FeederID char(9), FeederID2 char(9), FeederName char(50), Phasedesignation coded_domain("Phase Designation":smallint:4:R:2:Y:1:B:6:RY:3:YB:5:RB:7:RYB), Phasedesignation_resolved char(254), Voltage coded_domain(Voltage:smallint:120:"0.11 kV":160:"0.24 kV":210:"0.43 kV":90:"100 kV":340:"11 kV":110:"132 kV":360:"22 kV":380:"33 kV":80:"66 kV":150:"220 kV":260:"400 kV"), Voltage_resolved char(254), InsulationType coded_domain("SWG Insulation Type":char(7):MOCB:MOCB:OCB:OCB:VCB:VCB:GCB/SF6:GCB/SF6:T52/2E:T52/2E:Other:Other), InsulationType_resolved char(254), Mechanism coded_domain(Mechanism:smallint:1:Manual:2:Motorised:3:Compressor:4:Contactor:5:Motor/Manual:6:Contactor/Manual), Mechanism_resolved char(254), AuxiliarySupply coded_domain("Auxiliary Supply":char(2):AC:AC:DC:DC), AuxiliarySupply_resolved char(254), SymmetricalBreakingCurrent char(10), RatedPower char(50), CTPTCombined coded_domain(Yes/No:char(3):Yes:Yes:No:No), CTPTCombined_resolved char(254), DTCCode char(6), MakingCapacity char(50), OperatingSequence char(50), Make char(50), SerialNumber char(50), ManufacturingYear char(4),
      DateofCommissioning date, LastMaintenanceDate date, Warranty char(50), Cost char(10), AncillaryRole coded_domain(AncillaryRoleDomain:smallint:0:None:1:Source:2:Sink), AncillaryRole_resolved char(254), NormalStatus coded_domain("Normal Status":integer:0:Open:1:Close:2:"Not Applicable"), NormalStatus_resolved char(254), NormalPositionR coded_domain("Normal Status":integer:0:Open:1:Close:2:"Not Applicable"), NormalPositionR_resolved char(254), NormalPositionY coded_domain("Normal Status":integer:0:Open:1:Close:2:"Not Applicable"), NormalPositionY_resolved char(254), NormalPositionB coded_domain("Normal Status":integer:0:Open:1:Close:2:"Not Applicable"), NormalPositionB_resolved char(254), PresentPositionR coded_domain("Normal Status":integer:0:Open:1:Close:2:"Not Applicable"), PresentPositionR_resolved char(254), PresentPositionY coded_domain("Normal Status":integer:0:Open:1:Close:2:"Not Applicable"), PresentPositionY_resolved char(254), PresentPositionB coded_domain("Normal Status":integer:0:Open:1:Close:2:"Not Applicable"), PresentPositionB_resolved char(254), RatedCurrent coded_domain("Rated Current Switchgear":char(4):32:32:40:40:50:50:63:63:80:80:100:100:125:125:160:160:200:200:250:250:315:315:400:400:500:500:630:630:800:800:1000:1000:1250:1250:1600:1600:2000:2000:2500:2500:3150:3150:6:6:8:8:10:10:12:12:16:16:20:20:25:25), RatedCurrent_resolved char(254), FeederCode char(3), SAPFunctionalLocation char(50), ConnectionStatus coded_domain("Connection Status":char(50):1:Connected:2:Disconnected:3:Bypassed:4:Dismantle), ConnectionStatus_resolved char(254), Section_ coded_domain(Section:char(22):1112:DELTA:1111:"BRIT COLONY":1132:"SAHID NAGAR":1131:"BOARD COLONY":1222:"IRC NAYAPALLI":1221:BARAMUNDA:1223:"VSS NAGAR":1224:XAVIER:1231:BARANG:1234:GODISAHI:1235:KANANVIHAR:1214:"KHANDAGIRI S/O":1211:BHARATPUR:1213:KALINGANAGAR:1212:DUMUDUMA:1321:BARAGADA:1322:DHAULI:1316:"RASULAGARH S/O":1313:LAXMISAGAR:1314:MANCHESWAR:1315:PHULNAKHARA:1432:BALIPATNA:1431:BALAKATI:1433:BHARATIPUR:1421:GOP:1422:KONARK:1411:ASTARANG:2131:"JANKIA SEC OFF":2132:MALIPADA:2133:NIRAKARPUR:2141:HARIRAJPUR:2142:JANLA:2122:"BEGUNIA S/O":2121:BAGHAMARI:2124:RAJSUNAKHALA:2123:KALAPATHAR:2241:NAYAGARH:2244:"PERIPHERY S/O":2221:BOLAGARH:2234:KHANDAPADA:2233:KANTILO:2211:DASPALLA:2212:GANIA:2213:NUAGAON:2315:NACHUNI:2323:RANAPUR:2322:KUHUDI:2321:BHUSANDPUR:2412:KACHERI:2411:BALIAPANDA:2414:SWARGADWAR:2424:SADAR:2421:BRAHMAGIRI:2425:SUNAMUHI:2422:DELANGA:2423:KANAS:2433:"POWER HOUSE":2432:GHODABAZAR:2434:TALABANIA:2431:CHARINALA:2441:CHANDANPUR:2444:SATASANKHA:3111:"BUXI BAZAAR":3112:"COLLEGE SQUARE":3121:CITY:3122:"GANESH GHAT":3123:"KAZI BAZAAR":3124:"TOWN HALL":3131:CANTONMENT:3132:"CHANDNI CHOWK":3133:"TINKONIA BAGICHA":3143:TULSIPUR:3141:BIDANASI:3223:JOBRA:3222:JAGATPUR:3224:KANDARPUR:3221:MAUZA:3225:KISHORNAGAR:3212:DOLAMUNDAI:3231:CHAULIAGANJ:3232:"MAHANADI VIHAR":3321:CHARIBATIA:3332:BALIKUDA:3331:ADASPUR:3333:GOBINDAPUR:3311:BADACHANA:3312:BALICHANDRAPUR:3313:CHHATIA:3343:SITHALO:3423:KHUNTUNI:3425:TIGIRIA:3424:NUAPATNA:3413:NARASINGPUR:3411:BARAMBA:3412:KANPUR:3532:RAISUNGUDA:3531:BAHUGRAM:3513:"MAHANGA SEC OFF":3511:ERKANA:3512:KOTHAPADA:3522:"N KOILI":3521:ASURESWAR:3523:ORIKANTA:4111:BHAPUR:4121:"GONDIA SEC OFF":4122:JORANDA:4123:"NIHAL PRASAD":4144:"KANKADA HADA":4146:"R N PUR":4142:"K NAGAR":4141:BHUBAN:4145:"M K GOLA":4143:KALIAPANI:4132:"HINDOL ROAD S/O":4131:HINDOL:4133:KHAJURIAKATA:4214:BANTALA:4221:"BOINDA SEC OFF":4222:BAMUR:4223:ATHAMALLIK:4232:JARPADA:4231:CHHENDIPADA:4233:KOSALA:4312:"CHAINPAL SEC OFF":4313:MERAMANDALI:4311:BANARPAL:4345:"TALCHER SEC OFF":4341:HATATOTA:4344:"SOUTH BALANDA":4342:KANIHA:4343:SAMALA:4321:KHAMARA:4323:PARBIL:4324:RENGALI:5122:DANPUR:5123:INDUPUR:5121:CHHATA:5132:PATRAPUR:5131:DANDISAHI:5111:"AUL SEC OFF":5114:RAJKANIKA:5113:OLAVER:5112:BHUINPUR:5223:"MARSHAGHAI S/D":5224:NUAPADA:5221:GARADAPUR:5222:KORUA:5213:MAHAKALAPADA:5212:LUNA:5324:MANDASAHI:5321:DHIASAHI:5313:NAUGAON:5332:"RAGHUNATHPUR S/O":5331:BIRIDI:5422:"PARADEEP SEC OFF":5421:BHUTAMUNDAI:5433:TIRTOL:5431:ERSAMA:5432:KOLAR:5412:KUJANG:5413:RAHAMA:1121:"KARVEL NAGAR":1326:UTTARA:3211:BADAMBADI:3213:IND.ESTATE(OGP):5143:TALACHUA:5211:BABAR:5411:CHATUA:1325:"OLD TOWN-3":1114:UNIT-6:1122:UNIT-1:1123:UNIT-2:1134:"UNIT-9 ROAD":1133:"UNIT-9 FLAT":1232:"CS PUR-1":1233:"CS PUR-2":1323:"OLD TOWN-1":1324:"OLD TOWN-2":1311:KALPANA-1:1312:KALPANA-2:1423:NIMAPARA-1:1424:NIMAPARA-2:1412:KAKATPUR-1:1413:KAKATPUR-2:2143:JATANI-1:2144:JATANI-2:2111:BANKI-1:2112:BANKI-2:2113:BANKI-3:2245:SARANAKUL-1:2246:SARANAKUL-2:2242:ODAGAON-1:2243:ODAGAON-2:2222:ITAMATI-1:2223:ITAMATI-2:2311:BALUGAON-1:2312:BALUGAON-2:2313:BANAPUR-1:2314:BANAPUR-2:2324:TANGI-1:2325:TANGI-2:2442:SAKHIGOPAL-1:2443:SAKHIGOPAL-2:3113:RANIHAT-1:3114:RANIHAT-2:3322:CHOUDWAR-1:3323:CHOUDWAR-2:3421:ATHAGADA-1:3422:ATHAGADA-2:3533:SALIPUR-1:3534:SALIPUR-2:4112:"DKL SEC-1":4113:"DKL SEC-2":4114:"DKL SEC-3":4211:"ANGUL NO-1":4212:"ANGUL NO-2":4213:"ANGUL NO-3":4322:"PALLAHARA SEC OFF":4331:PARJANG-1:4332:PARJANG-2:5124:KENDRAPARA-1:5125:KENDRAPARA-2:5126:KENDRAPARA-3:5133:PATTAMUNDAI-1:5134:PATTAMUNDAI-2:5135:PATTAMUNDAI-3:5141:RAJNAGAR-1:5142:RAJNAGAR-2:5322:"J S PUR-1":5323:"J S PUR-2":5311:BALIKUDA-1:5312:BALIKUDA-2:1115:"POWER HOUSE-2":1113:"POWER HOUSE-1":1434:PIPILI-1:1435:PIPILI-2:2151:KHURDA-1:2152:KHURDA-2:2153:KHURDA-3:2154:KHURDA-4:2231:BHAPUR-1:2232:BHAPUR-2:3341:NIALI-1:3342:NIALI-2:3414:SECTION-4:2413:PASCHIMADWAR:3142:CDA:1124:UNIT-4), Section__resolved char(254), Subdivision coded_domain(Subdivision:char(14):1220:NAYAPALLI:1230:PERIPHERI:1210:KHANDAGIRI:1320:TEMPLE:1310:RASULGARH:1430:PIPILI:1420:NIMAPARA:1410:KAKATPUR:2130:JANKIA:2140:JATNI:2110:BANKI:2120:BEGUNIA:2240:NAYAGARH:2220:ITAMATI:2230:KHANDAPADA:2210:DASPALLA:2310:BALUGAON:2320:TANGI:2440:SAKHIGOPAL:3220:JOBRA:3210:BADAMBADI:3230:MAHANADIVIHAR:3320:CHOUDWAR:3330:GOPALPUR:3310:BADACHANA:3340:NIALI:3420:ATHAGADA:3410:NARASINGPUR:3530:SALIPUR:3510:MAHANGA:3520:"N KOILI":4110:DHENKANAL:4120:GONDIA:4140:"KAMAKHYA NAGAR":4130:"HINDOL ROAD":4210:ANGUL:4220:BOINDA:4230:CHENDIPADA:4310:CHAINPAL:4340:TALCHER:4320:PALLAHARA:4330:PARJANG:5120:KENDRAPARA:5130:PATTAMUNDAI:5140:RAJNAGAR:5110:AUL:5220:MARSHAGHAI:5210:MAHAKALAPADA:5320:JAGATSINGPUR:5310:BALIKUDA:5330:RAGHUNATHPUR:5420:PARADEEP:5430:TIRTOL:5410:KUJANGA:2150:KHURDA:1110:"SUB DIVISION-1,BBSR":1120:"SUB DIVISION-2,BBSR":1130:"SUB DIVISION-3,BBSR":2410:PURI-1:2420:PURI-2:2430:PURI-3:3110:"SUB DIVISION-1,CTC":3120:"SUB DIVISION-3,CTC":3130:"SUB DIVISION-4,CTC":3140:"SUB DIVISION-6,CTC"), Subdivision_resolved char(254),
      Division coded_domain(Division:char(6):1300:BED:1400:NED:2100:KHD:2200:NYED:2300:BAED:2400:PED:3300:CED:3400:AED:3500:SED:4100:DED:4200:ANED:4300:TED:5100:KED-1:5200:KED-2:5300:JED:5400:PDP:1100:BCDD-1:1200:BCDD-2:3100:CDD-1:3200:CDD-2), Division_resolved char(254), Circle coded_domain(Circle:char(6):3000:CTC:4000:DKL:5000:PDP:1000:BBSR-1:2000:BBSR-2), Circle_resolved char(254), Discom coded_domain(Discom:char(6):1:TPCODL), Discom_resolved char(254), WorkOrderID char(50), SurveyorRemark char(250), LocationCodeX double, LocationCodeY double, MMELECTRICTRACEWEIGHT integer, FEEDERINFO integer, RMUFacilityIDFK char(50), PillarFacilityIDFK char(50), StationFacilityIDFK char(50), created_user char(255), created_date date, last_edited_user char(255), last_edited_date date, Enabled coded_domain(EnabledDomain:smallint:0:False:1:True), Enabled_resolved char(254), Attachment char(250), EquipmentID integer
    -> AR_SWITCHGEAR
SUBSTATION (reader SDE30_1)
    attributes: OBJECTID integer, Name char(250), SubstationCode char(10), GISID char(50), NIN char(50), Address char(250), Subdivision char(50), Division char(50), Circle char(50), SubType smallint, SubstationLocation smallint, DistributionUtilityProperty smallint, PrimaryVoltage smallint, SecondaryVoltage smallint, No_Of_Inc_Feeder smallint, No_Of_Out_Feeder smallint, AllInComingFeederName char(250), AllOutGoingFeederName char(250), DateOfCommissioning date, TotalCapacityInMVA double, No_Of_Power_Transformer smallint, MaximumDemand char(10), Earth_Mat_With_Resistance char(10), Cost char(50), EAEquipment char(50), SAPID char(50), WorkOrderID char(50), SurveyorRemark char(250), Zone char(50), Section char(50),
      created_user char(255), created_date date, last_edited_user char(255), last_edited_date date, FeederCode char(50)
    -> AR_SUBSTATION
CIRCUITSOURCE (reader SDE30_1)
    attributes: OBJECTID integer, FeederName char(50), FeederSourceInfo integer, WorkOrderID char(50), FeederID char(12), FeederID2 char(12), FEEDERINFO integer, SubstationName char(50), SubstationID char(5), SwitchGearObjID integer, FeederCode char(3), ToSubstationID char(5)
    -> AttributeRemover
Substation (reader GEODATABASE_SDE_1)
    attributes: OBJECTID integer, Name char(250), SubstationCode char(5), GISID char(50), NIN char(50), SubType smallint, Address char(250), SubstationLocation coded_domain("Substation Location":smallint:1:Indoor:2:Outdoor), SubstationLocation_resolved char(254), DistributionUtilityProperty coded_domain(Yes/No:char(3):Yes:Yes:No:No), DistributionUtilityProperty_resolved char(254), PrimaryVoltage coded_domain("Primary Voltage":smallint:340:"11 kV":360:"22 kV":380:"33 kV":80:"66 kV":90:"100 kV":110:"132 kV":150:"220 kV":260:"400 kV"), PrimaryVoltage_resolved char(254), SecondaryVoltage coded_domain("Secondary Voltage":smallint:160:"0.24 kV":210:"0.43 kV":340:"11 kV":360:"22 kV":380:"33 kV":80:"66 kV":90:"100 kV":110:"132 kV"), SecondaryVoltage_resolved char(254), NoofIncomingFeeder coded_domain("No of Outgoing Feeder":smallint:1:1:2:2:3:3:4:4:5:5:6:6:7:7:8:8:9:9:10:10:11:11:12:12:13:13:14:14:15:15:16:16:17:17:18:18:19:19:20:20:21:21:22:22:23:23:24:24:25:25), NoofIncomingFeeder_resolved char(254), NoofOutgoingFeeder coded_domain("No of Outgoing Feeder":smallint:1:1:2:2:3:3:4:4:5:5:6:6:7:7:8:8:9:9:10:10:11:11:12:12:13:13:14:14:15:15:16:16:17:17:18:18:19:19:20:20:21:21:22:22:23:23:24:24:25:25), NoofOutgoingFeeder_resolved char(254), AllInComingFeederName char(250), AllOutGoingFeederName char(250), DateofCommissioning date, TotalCapacityInMVA double, NoofPowerTransformer smallint, MaximumDemand char(10), EarthMatWithResistance char(10), Cost char(10), WorkOrderID char(50), SurveyorRemark char(250), Section_ coded_domain(Section:char(22):1112:DELTA:1111:"BRIT COLONY":1132:"SAHID NAGAR":1131:"BOARD COLONY":1222:"IRC NAYAPALLI":1221:BARAMUNDA:1223:"VSS NAGAR":1224:XAVIER:1231:BARANG:1234:GODISAHI:1235:KANANVIHAR:1214:"KHANDAGIRI S/O":1211:BHARATPUR:1213:KALINGANAGAR:1212:DUMUDUMA:1321:BARAGADA:1322:DHAULI:1316:"RASULAGARH S/O":1313:LAXMISAGAR:1314:MANCHESWAR:1315:PHULNAKHARA:1432:BALIPATNA:1431:BALAKATI:1433:BHARATIPUR:1421:GOP:1422:KONARK:1411:ASTARANG:2131:"JANKIA SEC OFF":2132:MALIPADA:2133:NIRAKARPUR:2141:HARIRAJPUR:2142:JANLA:2122:"BEGUNIA S/O":2121:BAGHAMARI:2124:RAJSUNAKHALA:2123:KALAPATHAR:2241:NAYAGARH:2244:"PERIPHERY S/O":2221:BOLAGARH:2234:KHANDAPADA:2233:KANTILO:2211:DASPALLA:2212:GANIA:2213:NUAGAON:2315:NACHUNI:2323:RANAPUR:2322:KUHUDI:2321:BHUSANDPUR:2412:KACHERI:2411:BALIAPANDA:2414:SWARGADWAR:2424:SADAR:2421:BRAHMAGIRI:2425:SUNAMUHI:2422:DELANGA:2423:KANAS:2433:"POWER HOUSE":2432:GHODABAZAR:2434:TALABANIA:2431:CHARINALA:2441:CHANDANPUR:2444:SATASANKHA:3111:"BUXI BAZAAR":3112:"COLLEGE SQUARE":3121:CITY:3122:"GANESH GHAT":3123:"KAZI BAZAAR":3124:"TOWN HALL":3131:CANTONMENT:3132:"CHANDNI CHOWK":3133:"TINKONIA BAGICHA":3143:TULSIPUR:3141:BIDANASI:3223:JOBRA:3222:JAGATPUR:3224:KANDARPUR:3221:MAUZA:3225:KISHORNAGAR:3212:DOLAMUNDAI:3231:CHAULIAGANJ:3232:"MAHANADI VIHAR":3321:CHARIBATIA:3332:BALIKUDA:3331:ADASPUR:3333:GOBINDAPUR:3311:BADACHANA:3312:BALICHANDRAPUR:3313:CHHATIA:3343:SITHALO:3423:KHUNTUNI:3425:TIGIRIA:3424:NUAPATNA:3413:NARASINGPUR:3411:BARAMBA:3412:KANPUR:3532:RAISUNGUDA:3531:BAHUGRAM:3513:"MAHANGA SEC OFF":3511:ERKANA:3512:KOTHAPADA:3522:"N KOILI":3521:ASURESWAR:3523:ORIKANTA:4111:BHAPUR:4121:"GONDIA SEC OFF":4122:JORANDA:4123:"NIHAL PRASAD":4144:"KANKADA HADA":4146:"R N PUR":4142:"K NAGAR":4141:BHUBAN:4145:"M K GOLA":4143:KALIAPANI:4132:"HINDOL ROAD S/O":4131:HINDOL:4133:KHAJURIAKATA:4214:BANTALA:4221:"BOINDA SEC OFF":4222:BAMUR:4223:ATHAMALLIK:4232:JARPADA:4231:CHHENDIPADA:4233:KOSALA:4312:"CHAINPAL SEC OFF":4313:MERAMANDALI:4311:BANARPAL:4345:"TALCHER SEC OFF":4341:HATATOTA:4344:"SOUTH BALANDA":4342:KANIHA:4343:SAMALA:4321:KHAMARA:4323:PARBIL:4324:RENGALI:5122:DANPUR:5123:INDUPUR:5121:CHHATA:5132:PATRAPUR:5131:DANDISAHI:5111:"AUL SEC OFF":5114:RAJKANIKA:5113:OLAVER:5112:BHUINPUR:5223:"MARSHAGHAI S/D":5224:NUAPADA:5221:GARADAPUR:5222:KORUA:5213:MAHAKALAPADA:5212:LUNA:5324:MANDASAHI:5321:DHIASAHI:5313:NAUGAON:5332:"RAGHUNATHPUR S/O":5331:BIRIDI:5422:"PARADEEP SEC OFF":5421:BHUTAMUNDAI:5433:TIRTOL:5431:ERSAMA:5432:KOLAR:5412:KUJANG:5413:RAHAMA:1121:"KARVEL NAGAR":1326:UTTARA:3211:BADAMBADI:3213:IND.ESTATE(OGP):5143:TALACHUA:5211:BABAR:5411:CHATUA:1325:"OLD TOWN-3":1114:UNIT-6:1122:UNIT-1:1123:UNIT-2:1134:"UNIT-9 ROAD":1133:"UNIT-9 FLAT":1232:"CS PUR-1":1233:"CS PUR-2":1323:"OLD TOWN-1":1324:"OLD TOWN-2":1311:KALPANA-1:1312:KALPANA-2:1423:NIMAPARA-1:1424:NIMAPARA-2:1412:KAKATPUR-1:1413:KAKATPUR-2:2143:JATANI-1:2144:JATANI-2:2111:BANKI-1:2112:BANKI-2:2113:BANKI-3:2245:SARANAKUL-1:2246:SARANAKUL-2:2242:ODAGAON-1:2243:ODAGAON-2:2222:ITAMATI-1:2223:ITAMATI-2:2311:BALUGAON-1:2312:BALUGAON-2:2313:BANAPUR-1:2314:BANAPUR-2:2324:TANGI-1:2325:TANGI-2:2442:SAKHIGOPAL-1:2443:SAKHIGOPAL-2:3113:RANIHAT-1:3114:RANIHAT-2:3322:CHOUDWAR-1:3323:CHOUDWAR-2:3421:ATHAGADA-1:3422:ATHAGADA-2:3533:SALIPUR-1:3534:SALIPUR-2:4112:"DKL SEC-1":4113:"DKL SEC-2":4114:"DKL SEC-3":4211:"ANGUL NO-1":4212:"ANGUL NO-2":4213:"ANGUL NO-3":4322:"PALLAHARA SEC OFF":4331:PARJANG-1:4332:PARJANG-2:5124:KENDRAPARA-1:5125:KENDRAPARA-2:5126:KENDRAPARA-3:5133:PATTAMUNDAI-1:5134:PATTAMUNDAI-2:5135:PATTAMUNDAI-3:5141:RAJNAGAR-1:5142:RAJNAGAR-2:5322:"J S PUR-1":5323:"J S PUR-2":5311:BALIKUDA-1:5312:BALIKUDA-2:1115:"POWER HOUSE-2":1113:"POWER HOUSE-1":1434:PIPILI-1:1435:PIPILI-2:2151:KHURDA-1:2152:KHURDA-2:2153:KHURDA-3:2154:KHURDA-4:2231:BHAPUR-1:2232:BHAPUR-2:3341:NIALI-1:3342:NIALI-2:3414:SECTION-4:2413:PASCHIMADWAR:3142:CDA:1124:UNIT-4),
      Section__resolved char(254), Subdivision coded_domain(Subdivision:char(14):1220:NAYAPALLI:1230:PERIPHERI:1210:KHANDAGIRI:1320:TEMPLE:1310:RASULGARH:1430:PIPILI:1420:NIMAPARA:1410:KAKATPUR:2130:JANKIA:2140:JATNI:2110:BANKI:2120:BEGUNIA:2240:NAYAGARH:2220:ITAMATI:2230:KHANDAPADA:2210:DASPALLA:2310:BALUGAON:2320:TANGI:2440:SAKHIGOPAL:3220:JOBRA:3210:BADAMBADI:3230:MAHANADIVIHAR:3320:CHOUDWAR:3330:GOPALPUR:3310:BADACHANA:3340:NIALI:3420:ATHAGADA:3410:NARASINGPUR:3530:SALIPUR:3510:MAHANGA:3520:"N KOILI":4110:DHENKANAL:4120:GONDIA:4140:"KAMAKHYA NAGAR":4130:"HINDOL ROAD":4210:ANGUL:4220:BOINDA:4230:CHENDIPADA:4310:CHAINPAL:4340:TALCHER:4320:PALLAHARA:4330:PARJANG:5120:KENDRAPARA:5130:PATTAMUNDAI:5140:RAJNAGAR:5110:AUL:5220:MARSHAGHAI:5210:MAHAKALAPADA:5320:JAGATSINGPUR:5310:BALIKUDA:5330:RAGHUNATHPUR:5420:PARADEEP:5430:TIRTOL:5410:KUJANGA:2150:KHURDA:1110:"SUB DIVISION-1,BBSR":1120:"SUB DIVISION-2,BBSR":1130:"SUB DIVISION-3,BBSR":2410:PURI-1:2420:PURI-2:2430:PURI-3:3110:"SUB DIVISION-1,CTC":3120:"SUB DIVISION-3,CTC":3130:"SUB DIVISION-4,CTC":3140:"SUB DIVISION-6,CTC"), Subdivision_resolved char(254), Division coded_domain(Division:char(6):1300:BED:1400:NED:2100:KHD:2200:NYED:2300:BAED:2400:PED:3300:CED:3400:AED:3500:SED:4100:DED:4200:ANED:4300:TED:5100:KED-1:5200:KED-2:5300:JED:5400:PDP:1100:BCDD-1:1200:BCDD-2:3100:CDD-1:3200:CDD-2), Division_resolved char(254), Circle coded_domain(Circle:char(6):3000:CTC:4000:DKL:5000:PDP:1000:BBSR-1:2000:BBSR-2), Circle_resolved char(254), Discom coded_domain(Discom:char(6):1:TPCODL), Discom_resolved char(254), SAPFunctionalLocation char(50), FacilityID char(50), created_user char(255), created_date date, last_edited_user char(255), last_edited_date date, ShapeArea char(50), Attachment char(250), SHAPE.STArea() double, SHAPE.STLength() double
    -> AR_SUBSTATION
AR_SUBSTATION: AttributeRemover
    REMOVE_ATTRS = No_Of_Power_Transformer,created_date,created_user,Address,SubType,DistributionUtilityProperty,No_Of_Inc_Feeder,SubstationLocation,EAEquipment,OBJECTID,AllOutGoingFeederName,No_Of_Out_Feeder,Cost,DateOfCommissioning,Zone,Earth_Mat_With_Resistance,last_edited_user,WorkOrderID,AllInComingFeederName,SurveyorRemark,SAPID,last_edited_date,NIN,FeederCode,GISID
    -> FeatureMerger [SUPPLIER]
    -> TG_SUBSTATION (writer MSSQL_ADO_1)
TG_SUBSTATION (writer MSSQL_ADO_1)
    attributes: Name varchar(250), SubstationCode varchar(10), Subdivision varchar(50), Division varchar(50), Circle varchar(50), PrimaryVoltage smallint, SecondaryVoltage smallint, TotalCapacityInMVA float, MaximumDemand varchar(10), Section varchar(50), SubstationLocation_resolved varchar(254), DistributionUtilityProperty_resolved varchar(254), PrimaryVoltage_resolved varchar(254), SecondaryVoltage_resolved varchar(254), NoofIncomingFeeder char(54), NoofIncomingFeeder_resolved varchar(254), NoofOutgoingFeeder char(54), NoofOutgoingFeeder_resolved varchar(254), DateofCommissioning datetime, NoofPowerTransformer smallint, EarthMatWithResistance varchar(10), Section_ char(50), Section__resolved varchar(254), Subdivision_resolved varchar(254), Division_resolved varchar(254), Circle_resolved varchar(254), Discom char(29), Discom_resolved varchar(254), SAPFunctionalLocation varchar(50), FacilityID varchar(50),
      ShapeArea varchar(50), Attachment varchar(250), SHAPE.STArea() float, SHAPE.STLength() float
Circuit_Source (reader GEODATABASE_SDE_1)
    attributes: OBJECTID integer, FeederID char(12), FeederID2 char(12), FEEDERINFO integer, SubstationName char(50), SubstationID char(5), SwitchGearObjID integer, FeederName char(50), FeederSourceInfo integer, FeederCode char(3), WorkOrderID char(50), ToSubstationID char(5), GlobalID globalid
    -> AttributeRemover
AttributeRemover
    REMOVE_ATTRS = ToSubStationID,WorkOrderID,OBJECTID,FeederSourceInfo,FeederInfo
    -> TG_CIRCUITSOURCE (writer MSSQL_ADO_1)
    -> FeatureMerger [REQUESTOR]
TG_CIRCUITSOURCE (writer MSSQL_ADO_1)
    attributes: FeederID varchar(12), FeederID2 varchar(12), FEEDERINFO integer, SubstationName varchar(50), SubstationID varchar(5), SwitchGearObjID integer, FeederName varchar(50), FeederCode varchar(3), ToSubstationID varchar(5), GlobalID text
FeatureMerger
    ATTR_ACCUM_MODE = Merge Supplier
    ATTR_CONFLICT_RES = Use Requestor
    CLEANING_TOLERANCE = Automatic
    IGNORE_NULLS = No
    JOIN_KEYS = @Value(SubstationID) @Value(SubstationCode) AUTO
    MERGE_TYPE = Attributes Only
    PROCESS_DUPS = No
    REJECT_NULL_MISSING_KEYS = No
    SUPPLIERS_FIRST = No
    MERGED -> FeatureMerger_2 [REQUESTOR]
SWITCHGEAR (reader SDE30_1)
    attributes: OBJECTID integer, InstalledLocation smallint, LocationID char(50), GISID char(50), NIN char(50), FeederID char(12), FeederID2 char(12), FeederName char(50), Section char(22), Subdivision char(14), Division char(6), Circle char(6), Zone char(6), Phasedesignation smallint, Voltage smallint, SubType smallint, InsulationType char(7), Mechanism smallint, AuxiliarySupply char(2), SymmetricalBreakingCurrent char(10), RatedPower char(50), CTPTCombined char(3), MakingCapacity char(50), OperatingSequence char(50), Make char(50), SerialNumber char(50), ManufacturingYear char(4), LastMaintenanceDate date, Warranty char(50), Cost char(10),
      EAEquipment char(50), SAPID char(50), WorkOrderID char(50), SurveyorRemark char(250), MMELECTRICTRACEWEIGHT integer, AncillaryRole smallint, FEEDERINFO integer, created_user char(255), created_date date, last_edited_user char(255), last_edited_date date, Enabled smallint, NormalStatus integer, FeederCode char(3), DTCCode char(6), DateofCommissioning date, NormalPositionR integer, NormalPositionY integer, NormalPositionB integer, PresentPositionR integer, PresentPositionY integer, PresentPositionB integer, RatedCurrent char(4), EquipmentID integer, SAPFunctionalLocation char(50), ConnectionStatus char(50), LocationCodeX double, LocationCodeY double, RMUFacilityIDFK char(50), PillarFacilityIDFK char(50),
      StationFacilityIDFK char(50), CYMESubstationCode char(5), Town char(30)
    -> AR_SWITCHGEAR
AR_SWITCHGEAR: AttributeRemover
    REMOVE_ATTRS = Division,AuxiliarySupply,Section,last_edited_date,PresentPosition_Y,last_edited_user,EAEquipment,LocationID,Zone,ManufacturingYear,Make,SAPID,DTCCodeDetails,InstalledLocation,FeederName,LastMaintenanceDate,NIN,Subdivision,Voltage,FeederID2,Mechanism,NormalPosition_B,WorkOrderID,PresentPosition_B,SymmetricalBreakingCurrent,NormalPosition_A,SerialNumber,Warranty,FeederCode,SurveyorRemark,InsulationType,Phasedesignation,created_user,PresentPosition_R,NormalStatus,Cost,RatedPower,DateOfCommissioning,AncillaryRole,Enabled,MakingCapacity,Circle,LocationCode_X,NormalPosition_C,OperatingSequence,CTPTCombined,FEEDERINFO,MMELECTRICTRACEWEIGHT,created_date,LocationCode_Y
    -> AttributeCreator_8
AttributeCreator_8
    ATTR_TABLE = SET_TO CB_FeederId = @Value(FeederID)
    -> FeatureMerger_2 [SUPPLIER]
FeatureMerger_2
    ATTR_ACCUM_MODE = Merge Supplier
    ATTR_CONFLICT_RES = Use Requestor
    CLEANING_TOLERANCE = Automatic
    IGNORE_NULLS = No
    JOIN_KEYS = @Value(SwitchGearObjID) @Value(OBJECTID) AUTO @Value(FeederID) @Value(CB_FeederId) AUTO
    MERGE_TYPE = Attributes Only
    PROCESS_DUPS = No
    REJECT_NULL_MISSING_KEYS = No
    SUPPLIERS_FIRST = No
    MERGED -> AVM_FEEDERLIST_PRIV_2
AVM_FEEDERLIST_PRIV_5: AttributeValueMapper
    DIRECTION = Forward (Source To Destination)
    LUT = 01,ANGUL,02,BHUBANESWAR,03,CUTTACK,04,DHENKANAL,05,JAGATSINGHAPUR,06,JATNI,07,KENDRAPARA,08,KHORDHA,09,PARADEEP,10,PATTAMUNDAI,11,PURI,12,TALCHER
    SRC = Town
    VAL_ATTR = Town
    -> AVM_FEEDERLIST_PRIV_3
TG_FEEDERLIST (writer CSV2_1)
    attributes: SubstationId string, SwitchGearObjid string, FeederName string, FeederId string, Name string, SubstationCode string, Subdivision string, Division string, Circle string, PrimaryVoltage string, SecondaryVoltage string, TotalCapacityInMVA string, MaximumDemand string, OBJECTID string, GISID string, SubType string, Town string, Section string
TG_FEEDERLIST (writer MSSQL_ADO_1)
    attributes: Circle varchar(50), Division varchar(50), Subdivision varchar(50), Name varchar(250), SubstationCode varchar(10), PrimaryVoltage varchar(20), SecondaryVoltage varchar(20), TotalCapacityInMVA float, MaximumDemand varchar(10), FeederName varchar(50), FeederId varchar(40), GISID varchar(50), SwitchGearObjid integer, SubType smallint, Cheched char(20), Town char(20), Section char(50)

Bookmark: Area
AVM_FEEDERLIST_PRIV_2: AttributeValueMapper
    DEFAULT_VALUE = KV
    DIRECTION = Forward (Source To Destination)
    LUT = 11,BBSR1,12,BBSR2,13,CTC,14,DKL,15,PDP
    SRC = Circle
    VAL_ATTR = Circle
    -> AVM_FEEDERLIST_PRIV_5
AVM_FEEDERLIST_PRIV_3: AttributeValueMapper
    DEFAULT_VALUE = KV
    DIRECTION = Forward (Source To Destination)
    LUT = 1101,BCDD 1,1102,BCDD 2,1103,BED,1104,NED,1201,KHD,1202,NYD,1203,BAED,1204,PED,1301,CDD 1,1302,CDD 2,1303,CED,1304,AED,1305,SED,1401,DED,1402,ANED,1403,TED,1501,KED,1502,MED,1503,JED,1504,PDP
    SRC = Division
    VAL_ATTR = Division_Name
    -> AVM_FEEDERLIST_PRIV_4
AVM_FEEDERLIST_PRIV_4: AttributeValueMapper
    DEFAULT_VALUE = KV
    DIRECTION = Forward (Source To Destination)
    LUT = 110101,SDO 1,110102,SDO 2,110103,SDO 3,110201,NAYAPALLI,110202,PERIPHERI,110203,KHANDAGIRI,110301,TEMPLE,110302,RASULGARH,110403,PIPILI,110404,NIMAPARA,110405,KAKATPUR,120101,KHURDA,120102,JANKIA,120103,JATNI,120104,BANKI,120105,BEGUNIA,120201,NAYAGARH,120202,ITAMATI,120203,KHANDAPADA,120204,DASPALLA,120301,BALUGAON,120302,TANGI,120401,PURI 1,120402,PURI 2,120403,PURI 3,120404,SAKHIGOPAL,130101,SUB DIVISION 1,130103,SUB DIVISION 3,130104,SUB DIVISION 4,130106,SUB DIVISION 6,130201,JOBRA,130202,BADAMBADI,130203,MAHANADIVIHAR,130301,CHOUDWAR,130302,GOPALPUR,130303,BADACHANA,130304,NIALI,130401,ATHAGADA,130402,NARASINGPUR,130501,SALIPUR,130502,MAHANGA,130503,N KOILI,140101,DHENKANAL,140103,GONDIA,140104,K.NAGAR,140105,HINDOL ROAD,140201,ANGUL,140202,BOINDA,140203,CHENDIPADA,140301,CHAINPAL,140302,TALCHER,140303,PALLAHARA,140304,PARJANG,150101,KENDRAPARA,150102,PATTAMUNDAI,150103,RAJNAGAR,150104,AUL,150201,MARSHAGHAI,150202,MAHAKALAPADA,150301,JAGATSINGPUR,150303,BALIKUDA,150304,RAGHUNATHPUR,150401,PARADEEP,150402,TIRTOL,150403,KUJANGA
    SRC = Subdivision
    VAL_ATTR = Subdivision
    -> AVM_FEEDERLIST_PRIV

Bookmark: Voltge
AVM_FEEDERLIST_PRIV: AttributeValueMapper
    DEFAULT_VALUE = KV
    DIRECTION = Forward (Source To Destination)
    LUT = 340,11KV,360,22KV,380,33KV,80,66KV,90,100KV,110,132KV,150,220KV,260,400KV,120,0.11KV,160,0.24KV,210,0.43KV
    SRC = PrimaryVoltage
    VAL_ATTR = PrimaryVoltage
    -> AVM_FEEDERLIST_SECV
AVM_FEEDERLIST_SECV: AttributeValueMapper
    DEFAULT_VALUE = KV
    DIRECTION = Forward (Source To Destination)
    LUT = 340,11KV,360,22KV,380,33KV,80,66KV,90,100KV,110,132KV,150,220KV,260,400KV,120,0.11KV,160,0.24KV,210,0.43KV
    SRC = SecondaryVoltage
    VAL_ATTR = SecondaryVoltage
    -> TG_FEEDERLIST (writer CSV2_1)
    -> TG_FEEDERLIST (writer MSSQL_ADO_1)
