FME workspace custinfo.fmw

Parameters:
- SourceDataset_SDE30 =   # Source Esri ArcSDE Dataset
- DestDataset_MDB_ADO = D:\Nishant\CESU Project\Nishant\TechGration\TechGration\Feeder2\GISPGDB\Input_Data.mdb   # Database Path
- SourceDataset_MDB_ADO = D:\Nishant\CESU Project\Nishant\TechGration\TechGration\Feeder2\GISPGDB\Input_Data.mdb   # Database Path
- Password = ttpl@987

Readers:
- SDE30_1: SDE30 from $(SourceDataset_SDE30)
- MDB_ADO_1: MDB_ADO from $(SourceDataset_MDB_ADO)

Writers:
- MDB_ADO_2: MDB_ADO to $(DestDataset_MDB_ADO)

CONSUMERMETER (reader SDE30_1) [off]
    attributes: OBJECTID integer, Approachability char(255), Readability char(255), MeterOwnership char(255), MeterTestingStatus char(255), ViewingGlass char(255), MeterDisplay char(255), MeterSerialNumber char(255), MeterMake char(255), TypeofMeter char(255), MeterClass char(250), MeterReadingKwh double, ConnectionData char(255), ReddingDecimal char(255), SubMetering char(255), ManufacturingSeal char(255), MeterTestingSeal char(255), MeterBoxSeal char(255), MBSPaperSealSrNo char(255), MBSPlasticSealColour char(255), MaximumDemand char(255), ContractDemand char(255), AverageConsumption char(255), SanctionedLoad double, ConnectedLoad double, CurrentRating char(255), EAEquipment char(50), Subdivisioncode char(255), SectionCode char(50), Divisioncode char(50),
      CircleCode char(50), ZoneCode char(255), VillageCode char(50), RouteSequenceNo char(50), Remarks char(255), ConsumerNumber char(50), created_user char(255), created_date date, last_edited_user char(255), last_edited_date date
    -> AttributeRemover [off]
AttributeRemover [off]
    REMOVE_ATTRS = MBSPlasticSealColour,MeterTestingSeal,SubMetering,Readability,TypeofMeter,AverageConsumption,MBSPaperSealSrNo,created_user,VillageCode,ConnectionData,ReddingDecimal,ContractDemand,MaximumDemand,CurrentRating,Divisioncode,OBJECTID,created_date,ManufacturingSeal,MeterSerialNumber,SectionCode,ViewingGlass,Remarks,MeterMake,RouteSequenceNo,EAEquipment,MeterReadingKwh,Subdivisioncode,MeterTestingStatus,last_edited_user,MeterOwnership,MeterBoxSeal,ZoneCode,CircleCode,MeterClass,Approachability,last_edited_date,MeterDisplay
    -> FeatureMerger_3 [REQUESTOR] [off]
FeatureMerger_3 [off]
    IGNORE_NULLS = No
    REJECT_NULL_MISSING_KEYS = No
    JOIN_KEYS = @Value(ConsumerNumber) @Value(CESUConsumerNumber) AUTO
    ATTR_ACCUM_MODE = Merge Supplier
    ATTR_CONFLICT_RES = Use Requestor
    MERGE_TYPE = Attributes Only
    SUPPLIERS_FIRST = No
    PROCESS_DUPS = No
CONSUMERINFO (reader SDE30_1)
    attributes: OBJECTID integer, CESUConsumerNumber char(100), CIN char(255), NameOfConsumer char(255), FatherHusbandName char(255), ContactPersonForHT char(255), HouseNumber char(255), PlotNumber char(255), LaneNumber char(255), Locality char(255), RoadName char(255), Pincode char(50), Landmark char(255), LegacyAddress char(255), PhoneMobileNumber char(255), BankName char(255), BankAccountNumber char(255), IFSCCode char(255), EmailID char(255), Gender char(255), AadharNumber char(255), PANNumber char(255), MapPDFNumber char(255), MapBlockNumber char(255), NumberofFloors char(255), ConnectedToPole char(255), ConnectedToDTC char(255), BillingDTCode char(255), FeederCode char(50), FeederName char(255),
      SubstationCode char(50), SubstationName char(255), ConsumerStatus char(255), ServiceCondition char(255), TypeOfSupply char(255), ConnectedPhase smallint, ConductorCorrelation char(255), CustomerSupplyVoltage smallint, PurposeofConnection char(255), ConsumerClass char(255), CustomerSubtypeValue smallint, Generator char(255), TownCode char(10), TownName char(50), TariffCategory char(100), BuildingID char(50), CustomerType smallint, created_user char(255), created_date date, last_edited_user char(255), last_edited_date date
    -> AttributeRemover_2
    -> apdrp_fm_CONSUMERINFO (writer MDB_ADO_2)
apdrp_fm_CONSUMERINFO (writer MDB_ADO_2)
    attributes: OBJECTID long, CESUConsumerNumber text(100), CIN text(255), NameOfConsumer text(255), FatherHusbandName text(255), ContactPersonForHT text(255), HouseNumber text(255), PlotNumber text(255), LaneNumber text(255), Locality text(255), RoadName text(255), Pincode text(50), Landmark text(255), LegacyAddress text(255), PhoneMobileNumber text(255), BankName text(255), BankAccountNumber text(255), IFSCCode text(255), EmailID text(255), Gender text(255), AadharNumber text(255), PANNumber text(255), MapPDFNumber text(255), MapBlockNumber text(255), NumberofFloors text(255), ConnectedToPole text(255), ConnectedToDTC text(255), BillingDTCode text(255), FeederCode text(50), FeederName text(255),
      SubstationCode text(50), SubstationName text(255), ConsumerStatus text(255), ServiceCondition text(255), TypeOfSupply text(255), ConnectedPhase integer, ConductorCorrelation text(255), CustomerSupplyVoltage integer, PurposeofConnection text(255), ConsumerClass text(255), CustomerSubtypeValue integer, Generator text(255), TownCode text(10), TownName text(50), TariffCategory text(100), BuildingID text(50), CustomerType integer, created_user text(255), created_date datetime, last_edited_user text(255), last_edited_date datetime
AttributeRemover_2
    REMOVE_ATTRS = created_user,PlotNumber,HouseNumber,CustomerSupplyVoltage,Locality,RoadName,FeederName,EmailID,CIN,Landmark,PANNumber,BankAccountNumber,TariffCategory,AadharNumber,LaneNumber,BillingDTCode,FatherHusbandName,TownCode,last_edited_user,CustomerSubtypeValue,Generator,ContactPersonForHT,ConductorCorrelation,Pincode,MapPDFNumber,created_date,NameOfConsumer,NumberofFloors,MapBlockNumber,OBJECTID,Gender,BankName,last_edited_date,ConsumerClass,LegacyAddress,TownName,IFSCCode,PhoneMobileNumber
    -> AVM_HTCABLE_P
AVM_HTCABLE_P: AttributeValueMapper
    DEFAULT_VALUE = 0
    SRC = ConnectedPhase
    DIRECTION = Forward (Source To Destination)
    VAL_ATTR = TG_PHASE
    LUT = 1,A,2,B,4,C,7,ABC
    -> GIS_CONSUMERMETER_P (writer MDB_ADO_2)
    -> AttributeCreator_2
GIS_CONSUMERMETER_P (writer MDB_ADO_2)
    attributes: CESUConsumerNumber text(100), ConnectedToPole text(255), ConnectedToDTC text(255), FeederCode text(50), SubstationCode text(50), SubstationName text(255), ConsumerStatus text(255), ServiceCondition text(255), TypeOfSupply text(255), ConnectedPhase integer, PurposeofConnection text(255), BuildingID text(50), CustomerType integer, TG_PHASE text(200)
AttributeCreator_2
    ATTR_TABLE = SET_TO Year = @DateTimeNow()
    -> AVM_ConnectionStatus
AVM_ConnectionStatus: AttributeValueMapper
    DEFAULT_VALUE = 0
    SRC = ConsumerStatus
    DIRECTION = Forward (Source To Destination)
    VAL_ATTR = TG_ConsumerStatus
    LUT = 0,C,0,TC,1,TD,1,PD
    -> AttributeCreator
AttributeCreator
    ATTR_TABLE:
      SET_TO CustomerType = @Value(PurposeofConnection)
      SET_TO CustomerNumber = @Value(CESUConsumerNumber)
      SET_TO ConnectionStatus = @Value(TG_ConsumerStatus)
      SET_TO LoadPhase = @Value(TG_PHASE)
    -> FeatureMerger_2 [REQUESTOR]
LOADS (reader MDB_ADO_1)
    attributes: SECTIONID text(200), DeviceNumber text(200), LoadType text(50), BuildingID text(50)
    -> FeatureMerger_2 [SUPPLIER]
FeatureMerger_2
    IGNORE_NULLS = No
    REJECT_NULL_MISSING_KEYS = No
    JOIN_KEYS = @Value(BuildingID) @Value(BuildingID) AUTO
    ATTR_ACCUM_MODE = Merge Supplier
    ATTR_CONFLICT_RES = Use Requestor
    MERGE_TYPE = Attributes Only
    SUPPLIERS_FIRST = No
    PROCESS_DUPS = No
    MERGED -> TG_CUSTOMERLOADS (writer MDB_ADO_2)
    <REJECTED> -> EroorLoad (writer MDB_ADO_2)
TG_CUSTOMERLOADS (writer MDB_ADO_2)
    attributes: SECTIONID text(200), DeviceNumber text(200), LoadType text(200), CustomerNumber text(50), CustomerType text(50), ConnectionStatus text(200), LockDuringLoadAllocation text(200), Year text(4), LoadModelID text(200), NormalPriority text(200), EmergencyPriority text(200), ValueType text(200), LoadPhase text(200), Value1 text(200), Value2 text(200), ConnectedKVA text(200), KWH text(200), NumberOfCustomer text(200), CenterTapPercent text(200), CenterTapPercent2 text(200), LoadValue1N1 text(200), LoadValue1N2 text(200), LoadValue2N1 text(200), LoadValue2N2 text(200)
EroorLoad (writer MDB_ADO_2)
    attributes: SECTIONID text(200), DeviceNumber text(200), LoadType text(200), CustomerNumber text(50), CustomerType text(50), ConnectionStatus text(200), LockDuringLoadAllocation text(200), Year text(4), LoadModelID text(200), NormalPriority text(200), EmergencyPriority text(200), ValueType text(200), LoadPhase text(200), Value1 text(200), Value2 text(200), ConnectedKVA text(200), KWH text(200), NumberOfCustomer text(200), CenterTapPercent text(200), CenterTapPercent2 text(200), LoadValue1N1 text(200), LoadValue1N2 text(200), LoadValue2N1 text(200), LoadValue2N2 text(200)
